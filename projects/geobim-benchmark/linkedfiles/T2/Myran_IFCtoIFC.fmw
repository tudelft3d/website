FME workspace Myran_IFCtoIFC.fmw

Parameters:
- SourceDataset_IFC = C:\Users\dhintz\Dropbox (Safe Software Inc.)\DeanSafe\Projects\_StrategicProjects\GeoBIM\testData_ifc\Myran_fixed.ifc   # Source Industry Foundation Class (IFC) File(s)
- DestDataset_IFC = $(FME_MF_DIR)results\Myran_fme.ifc   # Destination Industry Foundation Class (IFC) File(s)
- IFC_VERSION_IFC = IFC2x3   # IFC Version

Readers:
- IFC_1: IFC from $(SourceDataset_IFC)

Writers:
- IFC_2: IFC to $(DestDataset_IFC)

Bookmark: Reader Feature Types
IfcBuildingElementProxy (reader IFC_1)
    attributes: GlobalId char(22), Name string, Description string, ObjectType string, Tag string, CompositionType enumeration, Axis geometry, Body geometry, Box geometry, FootPrint geometry, ifc_type_object_id string
    -> IfcBuildingElementProxy (writer IFC_2)
IfcBeam (reader IFC_1)
    attributes: GlobalId char(22), Name string, Description string, ObjectType string, Tag string, Axis geometry, Body geometry, Box geometry, FootPrint geometry, ifc_type_object_id string
    -> IfcBeam (writer IFC_2)
IfcBuilding (reader IFC_1)
    attributes: GlobalId char(22), Name string, Description string, ObjectType string, LongName string, CompositionType string, ElevationOfRefHeight real, ElevationOfTerrain real, BuildingAddress.Purpose enumeration, BuildingAddress.Description string, BuildingAddress.UserDefinedPurpose string, BuildingAddress.InternalLocation string, BuildingAddress.AddressLines string, BuildingAddress.PostalBox string, BuildingAddress.Town string, BuildingAddress.Region string, BuildingAddress.PostalCode string, BuildingAddress.Country string, Axis geometry, Body geometry, Box geometry, FootPrint geometry, ifc_type_object_id string
    -> IfcBuilding (writer IFC_2)
IfcBuildingStorey (reader IFC_1)
    attributes: GlobalId char(22), Name string, Description string, ObjectType string, LongName string, CompositionType enumeration, Elevation real, Axis geometry, Body geometry, Box geometry, FootPrint geometry, ifc_type_object_id string
    -> IfcBuildingStorey (writer IFC_2)
IfcColumn (reader IFC_1)
    attributes: GlobalId char(22), Name string, Description string, ObjectType string, Tag string, Axis geometry, Body geometry, Box geometry, FootPrint geometry, ifc_type_object_id string
    -> IfcColumn (writer IFC_2)
IfcCovering (reader IFC_1)
    attributes: GlobalId char(22), Name string, Description string, ObjectType string, Tag string, PredefinedType enumeration, Axis geometry, Body geometry, Box geometry, FootPrint geometry, ifc_type_object_id string
    -> IfcCovering (writer IFC_2)
IfcCurtainWall (reader IFC_1)
    attributes: GlobalId char(22), Name string, Description string, ObjectType string, Tag string, Axis geometry, Body geometry, Box geometry, FootPrint geometry, ifc_type_object_id string
    -> IfcCurtainWall (writer IFC_2)
IfcDoor (reader IFC_1)
    attributes: GlobalId char(22), Name string, Description string, ObjectType string, Tag string, OverallHeight real, OverallWidth real, Axis geometry, Body geometry, Box geometry, FootPrint geometry, ifc_type_object_id string
    -> IfcDoor (writer IFC_2)
IfcFlowSegment (reader IFC_1)
    attributes: GlobalId char(22), Name string, Description string, ObjectType string, Tag string, Axis geometry, Body geometry, Box geometry, FootPrint geometry, ifc_type_object_id string
    -> IfcFlowSegment (writer IFC_2)
IfcFlowTerminal (reader IFC_1)
    attributes: GlobalId char(22), Name string, Description string, ObjectType string, Tag string, Axis geometry, Body geometry, Box geometry, FootPrint geometry, ifc_type_object_id string
    -> IfcFlowTerminal (writer IFC_2)
IfcFurnishingElement (reader IFC_1)
    attributes: GlobalId char(22), Name string, Description string, ObjectType string, Tag string, Axis geometry, Body geometry, Box geometry, FootPrint geometry, ifc_type_object_id string
    -> IfcFurnishingElement (writer IFC_2)
IfcMember (reader IFC_1)
    attributes: GlobalId char(22), Name string, Description string, ObjectType string, Tag string, Axis geometry, Body geometry, Box geometry, FootPrint geometry, ifc_type_object_id string
    -> IfcMember (writer IFC_2)
IfcOpeningElement (reader IFC_1)
    attributes: GlobalId char(22), Name string, Description string, ObjectType string, Tag string, Axis geometry, Body geometry, Box geometry, FootPrint geometry, ifc_type_object_id string
    -> IfcOpeningElement (writer IFC_2)
IfcPlate (reader IFC_1)
    attributes: GlobalId char(22), Name string, Description string, ObjectType string, Tag string, Axis geometry, Body geometry, Box geometry, FootPrint geometry, ifc_type_object_id string
    -> IfcPlate (writer IFC_2)
IfcProject (reader IFC_1)
    attributes: GlobalId char(22), Name string, Description string, ObjectType string, LongName string, Phase string, Axis geometry, Body geometry, Box geometry, FootPrint geometry, ifc_type_object_id string
    -> IfcProject (writer IFC_2)
IfcRailing (reader IFC_1)
    attributes: GlobalId char(22), Name string, Description string, ObjectType string, Tag string, PredefinedType enumeration, Axis geometry, Body geometry, Box geometry, FootPrint geometry, ifc_type_object_id string
    -> IfcRailing (writer IFC_2)
IfcRoof (reader IFC_1)
    attributes: GlobalId char(22), Name string, Description string, ObjectType string, Tag string, ShapeType enumeration, Axis geometry, Body geometry, Box geometry, FootPrint geometry, ifc_type_object_id string
    -> IfcRoof (writer IFC_2)
IfcSite (reader IFC_1)
    attributes: GlobalId char(22), Name string, Description string, ObjectType string, LongName string, CompositionType string, RefLatitude real, RefLongitude real, RefElevation real, LandTitleNumber string, SiteAddress.Purpose enumeration, SiteAddress.Description string, SiteAddress.UserDefinedPurpose string, SiteAddress.InternalLocation string, SiteAddress.AddressLines string, SiteAddress.PostalBox string, SiteAddress.Town string, SiteAddress.Region string, SiteAddress.PostalCode string, SiteAddress.Country string, Axis geometry, Body geometry, Box geometry, FootPrint geometry, ifc_type_object_id string
    -> IfcSite (writer IFC_2)
IfcSlab (reader IFC_1)
    attributes: GlobalId char(22), Name string, Description string, ObjectType string, Tag string, PredefinedType enumeration, Axis geometry, Body geometry, Box geometry, FootPrint geometry, ifc_type_object_id string
    -> IfcSlab (writer IFC_2)
IfcStair (reader IFC_1)
    attributes: GlobalId char(22), Name string, Description string, ObjectType string, Tag string, ShapeType enumeration, Axis geometry, Body geometry, Box geometry, FootPrint geometry, ifc_type_object_id string
    -> IfcStair (writer IFC_2)
IfcStairFlight (reader IFC_1)
    attributes: GlobalId char(22), Name string, Description string, ObjectType string, Tag string, NumberOfRiser int, NumberOfTreads int, RiserHeight real, TreadLength real, Axis geometry, Body geometry, Box geometry, FootPrint geometry, ifc_type_object_id string
    -> IfcStairFlight (writer IFC_2)
IfcWall (reader IFC_1)
    attributes: GlobalId char(22), Name string, Description string, ObjectType string, Tag string, Axis geometry, Body geometry, Box geometry, FootPrint geometry, ifc_type_object_id string
    -> IfcWall (writer IFC_2)
IfcWallStandardCase (reader IFC_1)
    attributes: GlobalId char(22), Name string, Description string, ObjectType string, Tag string, Axis geometry, Body geometry, Box geometry, FootPrint geometry, ifc_type_object_id string
    -> IfcWallStandardCase (writer IFC_2)
IfcWindow (reader IFC_1)
    attributes: GlobalId char(22), Name string, Description string, ObjectType string, Tag string, OverallHeight real, OverallWidth real, Axis geometry, Body geometry, Box geometry, FootPrint geometry, ifc_type_object_id string
    -> IfcWindow (writer IFC_2)
IfcTypeObject (reader IFC_1)
    attributes: ifc_type_name string, GlobalId char(22), Name string, Description string, ApplicableOccurrence string, Tag string, ElementType string, PredefinedType string
    -> IfcTypeObject (writer IFC_2)
QuantitySetDefinition (reader IFC_1)
    attributes: ifc_quantities{}.name string, ifc_quantity_set_name string, ifc_quantities{}.type string
    -> QuantitySetDefinition (writer IFC_2)
PropertySetDefinition (reader IFC_1)
    attributes: ifc_properties{}.property_type string, ifc_properties{}.data_type string, ifc_properties{}.name string, ifc_property_set_name string
    -> PropertySetDefinition (writer IFC_2)

Bookmark: Writer Feature Types
IfcBuildingElementProxy (writer IFC_2)
    attributes: GlobalId char(22), Name string, Description string, ObjectType string, Tag string, CompositionType enumeration, Axis geometry, Body geometry, Box geometry, FootPrint geometry, ifc_parent_unique_id string, ifc_unique_id string, ifc_parent_id string, ifc_type_object_id string
IfcBeam (writer IFC_2)
    attributes: GlobalId char(22), Name string, Description string, ObjectType string, Tag string, Axis geometry, Body geometry, Box geometry, FootPrint geometry, ifc_parent_unique_id string, ifc_type_object_id string, ifc_unique_id string, ifc_parent_id string
IfcBuilding (writer IFC_2)
    attributes: GlobalId char(22), Name string, Description string, ObjectType string, LongName string, CompositionType string, ElevationOfRefHeight real, ElevationOfTerrain real, BuildingAddress.Purpose enumeration, BuildingAddress.Description string, BuildingAddress.UserDefinedPurpose string, BuildingAddress.InternalLocation string, BuildingAddress.AddressLines string, BuildingAddress.PostalBox string, BuildingAddress.Town string, BuildingAddress.Region string, BuildingAddress.PostalCode string, BuildingAddress.Country string, Axis geometry, Body geometry, Box geometry, FootPrint geometry, ifc_parent_unique_id string, ifc_unique_id string, ifc_parent_id string, ifc_type_object_id string
IfcBuildingStorey (writer IFC_2)
    attributes: GlobalId char(22), Name string, Description string, ObjectType string, LongName string, CompositionType enumeration, Elevation real, Axis geometry, Body geometry, Box geometry, FootPrint geometry, ifc_parent_unique_id string, ifc_unique_id string, ifc_parent_id string, ifc_type_object_id string
IfcColumn (writer IFC_2)
    attributes: GlobalId char(22), Name string, Description string, ObjectType string, Tag string, Axis geometry, Body geometry, Box geometry, FootPrint geometry, ifc_parent_unique_id string, ifc_unique_id string, ifc_parent_id string, ifc_type_object_id string
IfcCovering (writer IFC_2)
    attributes: GlobalId char(22), Name string, Description string, ObjectType string, Tag string, PredefinedType enumeration, Axis geometry, Body geometry, Box geometry, FootPrint geometry, ifc_parent_unique_id string, ifc_unique_id string, ifc_parent_id string, ifc_type_object_id string
IfcCurtainWall (writer IFC_2)
    attributes: GlobalId char(22), Name string, Description string, ObjectType string, Tag string, Axis geometry, Body geometry, Box geometry, FootPrint geometry, ifc_parent_unique_id string, ifc_unique_id string, ifc_parent_id string, ifc_type_object_id string
IfcDoor (writer IFC_2)
    attributes: GlobalId char(22), Name string, Description string, ObjectType string, Tag string, OverallHeight real, OverallWidth real, Axis geometry, Body geometry, Box geometry, FootPrint geometry, ifc_parent_unique_id string, ifc_unique_id string, ifc_parent_id string, ifc_type_object_id string
IfcFlowSegment (writer IFC_2)
    attributes: GlobalId char(22), Name string, Description string, ObjectType string, Tag string, Axis geometry, Body geometry, Box geometry, FootPrint geometry, ifc_parent_unique_id string, ifc_unique_id string, ifc_parent_id string, ifc_type_object_id string
IfcFlowTerminal (writer IFC_2)
    attributes: GlobalId char(22), Name string, Description string, ObjectType string, Tag string, Axis geometry, Body geometry, Box geometry, FootPrint geometry, ifc_parent_unique_id string, ifc_unique_id string, ifc_parent_id string, ifc_type_object_id string
IfcFurnishingElement (writer IFC_2)
    attributes: GlobalId char(22), Name string, Description string, ObjectType string, Tag string, Axis geometry, Body geometry, Box geometry, FootPrint geometry, ifc_parent_unique_id string, ifc_unique_id string, ifc_parent_id string, ifc_type_object_id string
IfcMember (writer IFC_2)
    attributes: GlobalId char(22), Name string, Description string, ObjectType string, Tag string, Axis geometry, Body geometry, Box geometry, FootPrint geometry, ifc_parent_unique_id string, ifc_unique_id string, ifc_parent_id string, ifc_type_object_id string
IfcOpeningElement (writer IFC_2)
    attributes: GlobalId char(22), Name string, Description string, ObjectType string, Tag string, Axis geometry, Body geometry, Box geometry, FootPrint geometry, ifc_parent_unique_id string, ifc_unique_id string, ifc_parent_id string, ifc_type_object_id string
IfcPlate (writer IFC_2)
    attributes: GlobalId char(22), Name string, Description string, ObjectType string, Tag string, Axis geometry, Body geometry, Box geometry, FootPrint geometry, ifc_parent_unique_id string, ifc_unique_id string, ifc_parent_id string, ifc_type_object_id string
IfcProject (writer IFC_2)
    attributes: GlobalId char(22), Name string, Description string, ObjectType string, LongName string, Phase string, Axis geometry, Body geometry, Box geometry, FootPrint geometry, ifc_parent_unique_id string, ifc_unique_id string, ifc_parent_id string, ifc_type_object_id string
IfcRailing (writer IFC_2)
    attributes: GlobalId char(22), Name string, Description string, ObjectType string, Tag string, PredefinedType enumeration, Axis geometry, Body geometry, Box geometry, FootPrint geometry, ifc_parent_unique_id string, ifc_unique_id string, ifc_parent_id string, ifc_type_object_id string
IfcRoof (writer IFC_2)
    attributes: GlobalId char(22), Name string, Description string, ObjectType string, Tag string, ShapeType enumeration, Axis geometry, Body geometry, Box geometry, FootPrint geometry, ifc_parent_unique_id string, ifc_unique_id string, ifc_parent_id string, ifc_type_object_id string
IfcSite (writer IFC_2)
    attributes: GlobalId char(22), Name string, Description string, ObjectType string, LongName string, CompositionType string, RefLatitude real, RefLongitude real, RefElevation real, LandTitleNumber string, SiteAddress.Purpose enumeration, SiteAddress.Description string, SiteAddress.UserDefinedPurpose string, SiteAddress.InternalLocation string, SiteAddress.AddressLines string, SiteAddress.PostalBox string, SiteAddress.Town string, SiteAddress.Region string, SiteAddress.PostalCode string, SiteAddress.Country string, Axis geometry, Body geometry, Box geometry, FootPrint geometry, ifc_parent_unique_id string, ifc_type_object_id string, ifc_parent_id string, ifc_unique_id string
IfcSlab (writer IFC_2)
    attributes: GlobalId char(22), Name string, Description string, ObjectType string, Tag string, PredefinedType enumeration, Axis geometry, Body geometry, Box geometry, FootPrint geometry, ifc_parent_unique_id string, ifc_type_object_id string, ifc_parent_id string, ifc_unique_id string
IfcStair (writer IFC_2)
    attributes: GlobalId char(22), Name string, Description string, ObjectType string, Tag string, ShapeType enumeration, Axis geometry, Body geometry, Box geometry, FootPrint geometry, ifc_parent_unique_id string, ifc_type_object_id string, ifc_parent_id string, ifc_unique_id string
IfcStairFlight (writer IFC_2)
    attributes: GlobalId char(22), Name string, Description string, ObjectType string, Tag string, NumberOfRiser int, NumberOfTreads int, RiserHeight real, TreadLength real, Axis geometry, Body geometry, Box geometry, FootPrint geometry, ifc_parent_unique_id string, ifc_unique_id string, ifc_parent_id string, ifc_type_object_id string
IfcWall (writer IFC_2)
    attributes: GlobalId char(22), Name string, Description string, ObjectType string, Tag string, Axis geometry, Body geometry, Box geometry, FootPrint geometry, ifc_parent_unique_id string, ifc_unique_id string, ifc_parent_id string, ifc_type_object_id string
IfcWallStandardCase (writer IFC_2)
    attributes: GlobalId char(22), Name string, Description string, ObjectType string, Tag string, Axis geometry, Body geometry, Box geometry, FootPrint geometry, ifc_parent_unique_id string, ifc_unique_id string, ifc_parent_id string, ifc_type_object_id string
IfcWindow (writer IFC_2)
    attributes: GlobalId char(22), Name string, Description string, ObjectType string, Tag string, OverallHeight real, OverallWidth real, Axis geometry, Body geometry, Box geometry, FootPrint geometry, ifc_parent_unique_id string, ifc_unique_id string, ifc_parent_id string, ifc_type_object_id string
IfcTypeObject (writer IFC_2)
    attributes: ifc_type_name string, ifc_unique_id string, GlobalId char(22), Name string, Description string, ApplicableOccurrence string, Tag string, ElementType string, PredefinedType string
QuantitySetDefinition (writer IFC_2)
    attributes: ifc_quantity_set_name string, ifc_quantities{}.name string, ifc_quantities{}.type string
PropertySetDefinition (writer IFC_2)
    attributes: ifc_properties{}.name string, ifc_properties{}.data_type string, ifc_property_set_name string, ifc_properties{}.property_type string
