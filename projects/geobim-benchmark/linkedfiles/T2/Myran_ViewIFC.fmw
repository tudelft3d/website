FME workspace Myran_ViewIFC.fmw

Parameters:
- SourceDataset_IFC = C:\Users\dhintz\Dropbox (Safe Software Inc.)\DeanSafe\Projects\_StrategicProjects\GeoBIM\testData_ifc\Myran_fixed.ifc   # Source Industry Foundation Class (IFC) File(s)

Readers:
- IFC_1: IFC from $(SourceDataset_IFC)

IfcBeam (reader IFC_1)
    attributes: GlobalId char(22), Name string, Description string, ObjectType string, Tag string, Axis geometry, Body geometry, Box geometry, FootPrint geometry, ifc_type_object_id string
    -> Scaler
IfcBuilding (reader IFC_1)
    attributes: GlobalId char(22), Name string, Description string, ObjectType string, LongName string, CompositionType string, ElevationOfRefHeight real, ElevationOfTerrain real, BuildingAddress.Purpose enumeration, BuildingAddress.Description string, BuildingAddress.UserDefinedPurpose string, BuildingAddress.InternalLocation string, BuildingAddress.AddressLines string, BuildingAddress.PostalBox string, BuildingAddress.Town string, BuildingAddress.Region string, BuildingAddress.PostalCode string, BuildingAddress.Country string, Axis geometry, Body geometry, Box geometry, FootPrint geometry, ifc_type_object_id string
    -> Scaler
IfcBuildingElementProxy (reader IFC_1)
    attributes: GlobalId char(22), Name string, Description string, ObjectType string, Tag string, CompositionType enumeration, Axis geometry, Body geometry, Box geometry, FootPrint geometry, ifc_type_object_id string
    -> Scaler
IfcBuildingStorey (reader IFC_1)
    attributes: GlobalId char(22), Name string, Description string, ObjectType string, LongName string, CompositionType enumeration, Elevation real, Axis geometry, Body geometry, Box geometry, FootPrint geometry, ifc_type_object_id string
    -> Scaler
IfcColumn (reader IFC_1)
    attributes: GlobalId char(22), Name string, Description string, ObjectType string, Tag string, Axis geometry, Body geometry, Box geometry, FootPrint geometry, ifc_type_object_id string
    -> Scaler
IfcCovering (reader IFC_1)
    attributes: GlobalId char(22), Name string, Description string, ObjectType string, Tag string, PredefinedType enumeration, Axis geometry, Body geometry, Box geometry, FootPrint geometry, ifc_type_object_id string
    -> Scaler
IfcCurtainWall (reader IFC_1)
    attributes: GlobalId char(22), Name string, Description string, ObjectType string, Tag string, Axis geometry, Body geometry, Box geometry, FootPrint geometry, ifc_type_object_id string
    -> Scaler
IfcDoor (reader IFC_1)
    attributes: GlobalId char(22), Name string, Description string, ObjectType string, Tag string, OverallHeight real, OverallWidth real, Axis geometry, Body geometry, Box geometry, FootPrint geometry, ifc_type_object_id string
    -> Scaler
IfcFlowSegment (reader IFC_1)
    attributes: GlobalId char(22), Name string, Description string, ObjectType string, Tag string, Axis geometry, Body geometry, Box geometry, FootPrint geometry, ifc_type_object_id string
    -> Scaler
IfcFlowTerminal (reader IFC_1)
    attributes: GlobalId char(22), Name string, Description string, ObjectType string, Tag string, Axis geometry, Body geometry, Box geometry, FootPrint geometry, ifc_type_object_id string
    -> Scaler
IfcFurnishingElement (reader IFC_1)
    attributes: GlobalId char(22), Name string, Description string, ObjectType string, Tag string, Axis geometry, Body geometry, Box geometry, FootPrint geometry, ifc_type_object_id string
    -> Scaler
IfcMember (reader IFC_1)
    attributes: GlobalId char(22), Name string, Description string, ObjectType string, Tag string, Axis geometry, Body geometry, Box geometry, FootPrint geometry, ifc_type_object_id string
    -> Scaler
IfcOpeningElement (reader IFC_1)
    attributes: GlobalId char(22), Name string, Description string, ObjectType string, Tag string, Axis geometry, Body geometry, Box geometry, FootPrint geometry, ifc_type_object_id string
    -> Scaler
IfcRailing (reader IFC_1)
    attributes: GlobalId char(22), Name string, Description string, ObjectType string, Tag string, PredefinedType enumeration, Axis geometry, Body geometry, Box geometry, FootPrint geometry, ifc_type_object_id string
    -> Scaler
IfcWallStandardCase (reader IFC_1)
    attributes: GlobalId char(22), Name string, Description string, ObjectType string, Tag string, Axis geometry, Body geometry, Box geometry, FootPrint geometry, ifc_type_object_id string
    -> Scaler
PropertySetDefinition (reader IFC_1)
    attributes: ifc_properties{}.data_type string, ifc_properties{}.property_type string, ifc_properties{}.name string, ifc_property_set_name string
    -> Scaler
QuantitySetDefinition (reader IFC_1)
    attributes: ifc_quantity_set_name string, ifc_quantities{}.type string, ifc_quantities{}.name string
    -> Scaler
IfcPlate (reader IFC_1)
    attributes: GlobalId char(22), Name string, Description string, ObjectType string, Tag string, Axis geometry, Body geometry, Box geometry, FootPrint geometry, ifc_type_object_id string
    -> Scaler
IfcProject (reader IFC_1)
    attributes: GlobalId char(22), Name string, Description string, ObjectType string, LongName string, Phase string, Axis geometry, Body geometry, Box geometry, FootPrint geometry, ifc_type_object_id string
    -> Scaler
IfcRoof (reader IFC_1)
    attributes: GlobalId char(22), Name string, Description string, ObjectType string, Tag string, ShapeType enumeration, Axis geometry, Body geometry, Box geometry, FootPrint geometry, ifc_type_object_id string
    -> Scaler
IfcSite (reader IFC_1)
    attributes: GlobalId char(22), Name string, Description string, ObjectType string, LongName string, CompositionType string, RefLatitude real, RefLongitude real, RefElevation real, LandTitleNumber string, SiteAddress.Purpose enumeration, SiteAddress.Description string, SiteAddress.UserDefinedPurpose string, SiteAddress.InternalLocation string, SiteAddress.AddressLines string, SiteAddress.PostalBox string, SiteAddress.Town string, SiteAddress.Region string, SiteAddress.PostalCode string, SiteAddress.Country string, Axis geometry, Body geometry, Box geometry, FootPrint geometry, ifc_type_object_id string
    -> Scaler
IfcSlab (reader IFC_1)
    attributes: GlobalId char(22), Name string, Description string, ObjectType string, Tag string, PredefinedType enumeration, Axis geometry, Body geometry, Box geometry, FootPrint geometry, ifc_type_object_id string
    -> Scaler
IfcStair (reader IFC_1)
    attributes: GlobalId char(22), Name string, Description string, ObjectType string, Tag string, ShapeType enumeration, Axis geometry, Body geometry, Box geometry, FootPrint geometry, ifc_type_object_id string
    -> Scaler
IfcStairFlight (reader IFC_1)
    attributes: GlobalId char(22), Name string, Description string, ObjectType string, Tag string, NumberOfRiser int, NumberOfTreads int, RiserHeight real, TreadLength real, Axis geometry, Body geometry, Box geometry, FootPrint geometry, ifc_type_object_id string
    -> Scaler
IfcTypeObject (reader IFC_1)
    attributes: ifc_type_name string, GlobalId char(22), Name string, Description string, ApplicableOccurrence string, Tag string, ElementType string, PredefinedType string
    -> Scaler
IfcWall (reader IFC_1)
    attributes: GlobalId char(22), Name string, Description string, ObjectType string, Tag string, Axis geometry, Body geometry, Box geometry, FootPrint geometry, ifc_type_object_id string
    -> Scaler
IfcWindow (reader IFC_1)
    attributes: GlobalId char(22), Name string, Description string, ObjectType string, Tag string, OverallHeight real, OverallWidth real, Axis geometry, Body geometry, Box geometry, FootPrint geometry, ifc_type_object_id string
    -> Scaler
Scaler
    RASTER_SCALING = Extents
    SCALE_ORIGIN = 0,0
    TEXT_LOC_ONLY = Location and Size
    XSCALE = 0.001
    YSCALE = 0.001
    ZSCALE = 0.001
    SCALED -> Offsetter
Offsetter
    MODE = Cartesian Coordinate
    XOFF = 145312.8320
    YOFF = 6721748.645
    ZOFF = 340.5
    OFFSET -> CoordinateSystemSetter
    <REJECTED> -> CoordinateSystemSetter
CoordinateSystemSetter
    COORDSYS = EPSG:3013
    -> Ifc_
Ifc_: Inspector
    TACKATTRS = fme_feature_type
