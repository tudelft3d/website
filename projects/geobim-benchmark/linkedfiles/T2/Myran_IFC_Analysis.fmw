FME workspace Myran_IFC_Analysis.fmw

Parameters:
- SourceDataset_IFC = C:\Users\dhintz\Dropbox (Safe Software Inc.)\DeanSafe\Projects\_StrategicProjects\GeoBIM\testData_ifc\Myran_fixed.ifc   # Source Industry Foundation Class (IFC) File(s)

Readers:
- IFC_1: IFC from $(SourceDataset_IFC)

IfcBuildingElementProxy (reader IFC_1)
    attributes: GlobalId char(22), Name string, Description string, ObjectType string, Tag string, CompositionType enumeration, Axis geometry, Body geometry, Box geometry, FootPrint geometry, ifc_type_object_id string
    -> Scaler
IfcBeam (reader IFC_1)
    attributes: GlobalId char(22), Name string, Description string, ObjectType string, Tag string, Axis geometry, Body geometry, Box geometry, FootPrint geometry, ifc_type_object_id string
    -> Scaler
IfcBuilding (reader IFC_1)
    attributes: GlobalId char(22), Name string, Description string, ObjectType string, LongName string, CompositionType string, ElevationOfRefHeight real, ElevationOfTerrain real, BuildingAddress.Purpose enumeration, BuildingAddress.Description string, BuildingAddress.UserDefinedPurpose string, BuildingAddress.InternalLocation string, BuildingAddress.AddressLines string, BuildingAddress.PostalBox string, BuildingAddress.Town string, BuildingAddress.Region string, BuildingAddress.PostalCode string, BuildingAddress.Country string, Axis geometry, Body geometry, Box geometry, FootPrint geometry, ifc_type_object_id string
    -> Scaler
IfcBuildingStorey (reader IFC_1)
    attributes: GlobalId char(22), Name string, Description string, ObjectType string, LongName string, CompositionType enumeration, Elevation real, Axis geometry, Body geometry, Box geometry, FootPrint geometry, ifc_type_object_id string
    -> Scaler
IfcColumn (reader IFC_1)
    attributes: GlobalId char(22), Name string, Description string, ObjectType string, Tag string, Axis geometry, Body geometry, Box geometry, FootPrint geometry, ifc_type_object_id string
    -> Scaler
IfcCovering (reader IFC_1)
    attributes: GlobalId char(22), Name string, Description string, ObjectType string, Tag string, PredefinedType enumeration, Axis geometry, Body geometry, Box geometry, FootPrint geometry, ifc_type_object_id string
    -> Scaler
IfcCurtainWall (reader IFC_1)
    attributes: GlobalId char(22), Name string, Description string, ObjectType string, Tag string, Axis geometry, Body geometry, Box geometry, FootPrint geometry, ifc_type_object_id string
    -> Scaler
IfcDoor (reader IFC_1)
    attributes: GlobalId char(22), Name string, Description string, ObjectType string, Tag string, OverallHeight real, OverallWidth real, Axis geometry, Body geometry, Box geometry, FootPrint geometry, ifc_type_object_id string
    -> Scaler
IfcFlowSegment (reader IFC_1)
    attributes: GlobalId char(22), Name string, Description string, ObjectType string, Tag string, Axis geometry, Body geometry, Box geometry, FootPrint geometry, ifc_type_object_id string
    -> Scaler
IfcFlowTerminal (reader IFC_1)
    attributes: GlobalId char(22), Name string, Description string, ObjectType string, Tag string, Axis geometry, Body geometry, Box geometry, FootPrint geometry, ifc_type_object_id string
    -> Scaler
IfcFurnishingElement (reader IFC_1)
    attributes: GlobalId char(22), Name string, Description string, ObjectType string, Tag string, Axis geometry, Body geometry, Box geometry, FootPrint geometry, ifc_type_object_id string
    -> Scaler
IfcMember (reader IFC_1)
    attributes: GlobalId char(22), Name string, Description string, ObjectType string, Tag string, Axis geometry, Body geometry, Box geometry, FootPrint geometry, ifc_type_object_id string
    -> Scaler
IfcOpeningElement (reader IFC_1)
    attributes: GlobalId char(22), Name string, Description string, ObjectType string, Tag string, Axis geometry, Body geometry, Box geometry, FootPrint geometry, ifc_type_object_id string
    -> Scaler
IfcRailing (reader IFC_1)
    attributes: GlobalId char(22), Name string, Description string, ObjectType string, Tag string, PredefinedType enumeration, Axis geometry, Body geometry, Box geometry, FootPrint geometry, ifc_type_object_id string
    -> Scaler
IfcWallStandardCase (reader IFC_1)
    attributes: GlobalId char(22), Name string, Description string, ObjectType string, Tag string, Axis geometry, Body geometry, Box geometry, FootPrint geometry, ifc_type_object_id string
    -> Scaler
PropertySetDefinition (reader IFC_1)
    attributes: ifc_properties{}.data_type string, ifc_properties{}.property_type string, ifc_properties{}.name string, ifc_property_set_name string
    -> Scaler
QuantitySetDefinition (reader IFC_1)
    attributes: ifc_quantity_set_name string, ifc_quantities{}.type string, ifc_quantities{}.name string
    -> Scaler
IfcPlate (reader IFC_1)
    attributes: GlobalId char(22), Name string, Description string, ObjectType string, Tag string, Axis geometry, Body geometry, Box geometry, FootPrint geometry, ifc_type_object_id string
    -> Scaler
IfcProject (reader IFC_1)
    attributes: GlobalId char(22), Name string, Description string, ObjectType string, LongName string, Phase string, Axis geometry, Body geometry, Box geometry, FootPrint geometry, ifc_type_object_id string
    -> Scaler
IfcRoof (reader IFC_1)
    attributes: GlobalId char(22), Name string, Description string, ObjectType string, Tag string, ShapeType enumeration, Axis geometry, Body geometry, Box geometry, FootPrint geometry, ifc_type_object_id string
    -> Scaler
IfcSite (reader IFC_1)
    attributes: GlobalId char(22), Name string, Description string, ObjectType string, LongName string, CompositionType string, RefLatitude real, RefLongitude real, RefElevation real, LandTitleNumber string, SiteAddress.Purpose enumeration, SiteAddress.Description string, SiteAddress.UserDefinedPurpose string, SiteAddress.InternalLocation string, SiteAddress.AddressLines string, SiteAddress.PostalBox string, SiteAddress.Town string, SiteAddress.Region string, SiteAddress.PostalCode string, SiteAddress.Country string, Axis geometry, Body geometry, Box geometry, FootPrint geometry, ifc_type_object_id string
    -> Scaler
IfcSlab (reader IFC_1)
    attributes: GlobalId char(22), Name string, Description string, ObjectType string, Tag string, PredefinedType enumeration, Axis geometry, Body geometry, Box geometry, FootPrint geometry, ifc_type_object_id string
    -> Scaler
IfcStair (reader IFC_1)
    attributes: GlobalId char(22), Name string, Description string, ObjectType string, Tag string, ShapeType enumeration, Axis geometry, Body geometry, Box geometry, FootPrint geometry, ifc_type_object_id string
    -> Scaler
IfcStairFlight (reader IFC_1)
    attributes: GlobalId char(22), Name string, Description string, ObjectType string, Tag string, NumberOfRiser int, NumberOfTreads int, RiserHeight real, TreadLength real, Axis geometry, Body geometry, Box geometry, FootPrint geometry, ifc_type_object_id string
    -> Scaler
IfcTypeObject (reader IFC_1)
    attributes: ifc_type_name string, GlobalId char(22), Name string, Description string, ApplicableOccurrence string, Tag string, ElementType string, PredefinedType string
    -> Scaler
IfcWall (reader IFC_1)
    attributes: GlobalId char(22), Name string, Description string, ObjectType string, Tag string, Axis geometry, Body geometry, Box geometry, FootPrint geometry, ifc_type_object_id string
    -> Scaler
IfcWindow (reader IFC_1)
    attributes: GlobalId char(22), Name string, Description string, ObjectType string, Tag string, OverallHeight real, OverallWidth real, Axis geometry, Body geometry, Box geometry, FootPrint geometry, ifc_type_object_id string
    -> Scaler
Scaler
    RASTER_SCALING = Extents
    SCALE_ORIGIN = 0,0
    TEXT_LOC_ONLY = Location and Size
    XSCALE = 0.001
    YSCALE = 0.001
    ZSCALE = 0.001
    SCALED -> Offsetter
Offsetter
    MODE = Cartesian Coordinate
    XOFF = 145312.8320
    YOFF = 6721748.645
    ZOFF = 340.5
    OFFSET -> CoordinateSystemSetter
    <REJECTED> -> CoordinateSystemSetter
CoordinateSystemSetter
    COORDSYS = EPSG:3013
    -> GeometryValidator
Note: GeometryValidator [GeometryValidator] / Validation: / Set of Issues to Detect: Surfaces And Solids Issue To DetectParametersSelf-Intersections in 2DParameters: / Check Self-Touching Polygon: No / Connect Z Mode: First Wins / Tolerance: None / Contains Non-Planar SurfacesParameters: / Also Check Areas: No / Thickness Mode: Automatic / Angular Mode: Automatic / Invalid Solid VoidsInvalid Solid BoundariesFlip Appearances: Flip Appearances / Missing Texture CoordinatesSurface OrientationSolid OrientationOutput: / Detected Issue List Name: _issues / Attempt Repair: Yes / Summary mode: Detailed
GeometryValidator
    ISSUE_ATTR_NAME = _issues
    PRESETS = Surfaces And Solids
    REPAIR = Yes
    RULES = SELF_INTERSECTING CHECK_HOLE_TOUCHING_POLYGON]No]CONNECT_Z_MODE_SI]FIRST_WINS]SELF_INTERSECTION_TOLERANCE]None]FME_CONTROLLER_QUERY_FILE]transformers\dependencies\geometryvalidator\SELF_INTERSECTING.fme PLANAR_SURFACE CHECK_AREA]DO_NOT_CHECK_AREA]TOLERANCE_MODE]AUTO]TOLERANCE]0.0]ANGULAR_TOLERANCE_MODE]AUTO]ANGULAR_TOLERANCE]0.0]FME_CONTROLLER_QUERY_FILE]transformers\dependencies\geometryvalidator\PLANAR_SURFACE.fme SOLID_VOID_REPAIR  SHELL_VALIDATION FLIP_APPEARANCE_MODE]FLIP_APPEARANCES]FME_CONTROLLER_QUERY_FILE]transformers\dependencies\geometryvalidator\SHELL_VALIDATION.fme MISSING_TEXTURE_COORDINATES  SURFACE_ORIENTATION  SOLID_ORIENTATION
    SUMMARY = Detailed
    PASSED -> VolumeCalculator
    FAILED -> BadGeometry_
    REPAIRED -> Myran_
    INVALID_PARTS -> Myran_
    <REJECTED> -> Myran_
VolumeCalculator
    MULT = 1
    SET_TRAIT = No
    VOLUME_ATTR = _volume
    -> Myran_
Myran_: Inspector
    TACKATTRS = fme_feature_type
BadGeometry_: Inspector
    TACKATTRS = fme_feature_type
