FME workspace MyranIFC_georeference.fmw

Parameters:
- SourceDataset_IFC = C:\Users\dhintz\Dropbox (Safe Software Inc.)\DeanSafe\Projects\_StrategicProjects\GeoBIM\testData_ifc\Myran_fixed.ifc   # Source Industry Foundation Class (IFC) File(s)
- DestDataset_IFC = C:\Users\dhintz\Dropbox (Safe Software Inc.)\DeanSafe\Projects\_StrategicProjects\GeoBIM\Task2_IFCgeoreferencing\Output\Task2_MyranExport_georeferenced_epsg3031_fme.ifc   # Destination Industry Foundation Class (IFC) File(s)

Readers:
- IFC_1: IFC from $(SourceDataset_IFC)

Writers:
- IFC_2: IFC to $(DestDataset_IFC)

IfcBuildingElementProxy (reader IFC_1)
    attributes: GlobalId char(22), Name string, Description string, ObjectType string, Tag string, CompositionType enumeration, Axis geometry, Body geometry, Box geometry, FootPrint geometry, ifc_type_object_id string
    -> Scaler
IfcBeam (reader IFC_1)
    attributes: GlobalId char(22), Name string, Description string, ObjectType string, Tag string, Axis geometry, Body geometry, Box geometry, FootPrint geometry, ifc_type_object_id string
    -> Scaler
IfcBuilding (reader IFC_1)
    attributes: GlobalId char(22), Name string, Description string, ObjectType string, LongName string, CompositionType string, ElevationOfRefHeight real, ElevationOfTerrain real, BuildingAddress.Purpose enumeration, BuildingAddress.Description string, BuildingAddress.UserDefinedPurpose string, BuildingAddress.InternalLocation string, BuildingAddress.AddressLines string, BuildingAddress.PostalBox string, BuildingAddress.Town string, BuildingAddress.Region string, BuildingAddress.PostalCode string, BuildingAddress.Country string, Axis geometry, Body geometry, Box geometry, FootPrint geometry, ifc_type_object_id string
    -> Scaler
IfcBuildingStorey (reader IFC_1)
    attributes: GlobalId char(22), Name string, Description string, ObjectType string, LongName string, CompositionType enumeration, Elevation real, Axis geometry, Body geometry, Box geometry, FootPrint geometry, ifc_type_object_id string
    -> Scaler
IfcColumn (reader IFC_1)
    attributes: GlobalId char(22), Name string, Description string, ObjectType string, Tag string, Axis geometry, Body geometry, Box geometry, FootPrint geometry, ifc_type_object_id string
    -> Scaler
IfcCovering (reader IFC_1)
    attributes: GlobalId char(22), Name string, Description string, ObjectType string, Tag string, PredefinedType enumeration, Axis geometry, Body geometry, Box geometry, FootPrint geometry, ifc_type_object_id string
    -> Scaler
IfcCurtainWall (reader IFC_1)
    attributes: GlobalId char(22), Name string, Description string, ObjectType string, Tag string, Axis geometry, Body geometry, Box geometry, FootPrint geometry, ifc_type_object_id string
    -> Scaler
IfcDoor (reader IFC_1)
    attributes: GlobalId char(22), Name string, Description string, ObjectType string, Tag string, OverallHeight real, OverallWidth real, Axis geometry, Body geometry, Box geometry, FootPrint geometry, ifc_type_object_id string
    -> Scaler
IfcFlowSegment (reader IFC_1)
    attributes: GlobalId char(22), Name string, Description string, ObjectType string, Tag string, Axis geometry, Body geometry, Box geometry, FootPrint geometry, ifc_type_object_id string
    -> Scaler
IfcFlowTerminal (reader IFC_1)
    attributes: GlobalId char(22), Name string, Description string, ObjectType string, Tag string, Axis geometry, Body geometry, Box geometry, FootPrint geometry, ifc_type_object_id string
    -> Scaler
IfcFurnishingElement (reader IFC_1)
    attributes: GlobalId char(22), Name string, Description string, ObjectType string, Tag string, Axis geometry, Body geometry, Box geometry, FootPrint geometry, ifc_type_object_id string
    -> Scaler
IfcMember (reader IFC_1)
    attributes: GlobalId char(22), Name string, Description string, ObjectType string, Tag string, Axis geometry, Body geometry, Box geometry, FootPrint geometry, ifc_type_object_id string
    -> Scaler
IfcOpeningElement (reader IFC_1)
    attributes: GlobalId char(22), Name string, Description string, ObjectType string, Tag string, Axis geometry, Body geometry, Box geometry, FootPrint geometry, ifc_type_object_id string
    -> Scaler
IfcRailing (reader IFC_1)
    attributes: GlobalId char(22), Name string, Description string, ObjectType string, Tag string, PredefinedType enumeration, Axis geometry, Body geometry, Box geometry, FootPrint geometry, ifc_type_object_id string
    -> Scaler
IfcWallStandardCase (reader IFC_1)
    attributes: GlobalId char(22), Name string, Description string, ObjectType string, Tag string, Axis geometry, Body geometry, Box geometry, FootPrint geometry, ifc_type_object_id string
    -> Scaler
PropertySetDefinition (reader IFC_1)
    attributes: ifc_properties{}.data_type string, ifc_properties{}.property_type string, ifc_properties{}.name string, ifc_property_set_name string
    -> Scaler
QuantitySetDefinition (reader IFC_1)
    attributes: ifc_quantity_set_name string, ifc_quantities{}.type string, ifc_quantities{}.name string
    -> Scaler
IfcPlate (reader IFC_1)
    attributes: GlobalId char(22), Name string, Description string, ObjectType string, Tag string, Axis geometry, Body geometry, Box geometry, FootPrint geometry, ifc_type_object_id string
    -> Scaler
IfcProject (reader IFC_1)
    attributes: GlobalId char(22), Name string, Description string, ObjectType string, LongName string, Phase string, Axis geometry, Body geometry, Box geometry, FootPrint geometry, ifc_type_object_id string
    -> Scaler
IfcRoof (reader IFC_1)
    attributes: GlobalId char(22), Name string, Description string, ObjectType string, Tag string, ShapeType enumeration, Axis geometry, Body geometry, Box geometry, FootPrint geometry, ifc_type_object_id string
    -> Scaler
IfcSite (reader IFC_1)
    attributes: GlobalId char(22), Name string, Description string, ObjectType string, LongName string, CompositionType string, RefLatitude real, RefLongitude real, RefElevation real, LandTitleNumber string, SiteAddress.Purpose enumeration, SiteAddress.Description string, SiteAddress.UserDefinedPurpose string, SiteAddress.InternalLocation string, SiteAddress.AddressLines string, SiteAddress.PostalBox string, SiteAddress.Town string, SiteAddress.Region string, SiteAddress.PostalCode string, SiteAddress.Country string, Axis geometry, Body geometry, Box geometry, FootPrint geometry, ifc_type_object_id string
    -> Scaler
IfcSlab (reader IFC_1)
    attributes: GlobalId char(22), Name string, Description string, ObjectType string, Tag string, PredefinedType enumeration, Axis geometry, Body geometry, Box geometry, FootPrint geometry, ifc_type_object_id string
    -> Scaler
IfcStair (reader IFC_1)
    attributes: GlobalId char(22), Name string, Description string, ObjectType string, Tag string, ShapeType enumeration, Axis geometry, Body geometry, Box geometry, FootPrint geometry, ifc_type_object_id string
    -> Scaler
IfcStairFlight (reader IFC_1)
    attributes: GlobalId char(22), Name string, Description string, ObjectType string, Tag string, NumberOfRiser int, NumberOfTreads int, RiserHeight real, TreadLength real, Axis geometry, Body geometry, Box geometry, FootPrint geometry, ifc_type_object_id string
    -> Scaler
IfcTypeObject (reader IFC_1)
    attributes: ifc_type_name string, GlobalId char(22), Name string, Description string, ApplicableOccurrence string, Tag string, ElementType string, PredefinedType string
    -> Scaler
IfcWall (reader IFC_1)
    attributes: GlobalId char(22), Name string, Description string, ObjectType string, Tag string, Axis geometry, Body geometry, Box geometry, FootPrint geometry, ifc_type_object_id string
    -> Scaler
IfcWindow (reader IFC_1)
    attributes: GlobalId char(22), Name string, Description string, ObjectType string, Tag string, OverallHeight real, OverallWidth real, Axis geometry, Body geometry, Box geometry, FootPrint geometry, ifc_type_object_id string
    -> Scaler
Note: Scaler [Scaler] / Scale Factors: / X: 0.001 / Y: 0.001 / Z: 0.001 / Parameters: / Text Scaling: Location and Size / Raster Scaling: Extents / Scale Origin: 0,0 / Point Cloud: / Point Cloud Components to Scale: <not set>
Scaler
    RASTER_SCALING = Extents
    SCALE_ORIGIN = 0,0
    TEXT_LOC_ONLY = Location and Size
    XSCALE = 0.001
    YSCALE = 0.001
    ZSCALE = 0.001
    SCALED -> Offsetter
Note: Offsetter [Offsetter] / Parameters: / Mode: Cartesian Coordinate / Cartesian Coordinate Parameters: / X Offset: 145312.8320 / Y Offset: 6721748.645 / Z Offset: 340.5 / Point Cloud: / Point Cloud Components to Offset: <not set>
Offsetter
    MODE = Cartesian Coordinate
    XOFF = 145312.8320
    YOFF = 6721748.645
    ZOFF = 340.5
    OFFSET -> CoordinateSystemSetter
    <REJECTED> -> CoordinateSystemSetter
Note: CoordinateSystemSetter [CoordinateSystemSetter] / Parameters: / Coordinate System: EPSG:3013
CoordinateSystemSetter
    COORDSYS = EPSG:3013
    -> FeatureTypeFilter
FeatureTypeFilter
    ATTRIBUTES = <Blank>,<Unfiltered>,IfcSite,IfcBeam,IfcBuilding,IfcBuildingElementProxy,IfcBuildingStorey,IfcColumn,IfcCovering,IfcCurtainWall,IfcDoor,IfcFlowSegment,IfcFlowTerminal,IfcFurnishingElement,IfcMember,IfcOpeningElement,IfcPlate,IfcProject,IfcRailing,IfcRoof,IfcSlab,IfcStair,IfcStairFlight,IfcWall,IfcWallStandardCase,IfcWindow,IfcTypeObject,QuantitySetDefinition,PropertySetDefinition
    IfcSite -> GeometryExtractor
    IfcSite -> FeatureMerger [REQUESTOR]
    IfcBeam -> IfcBeam (writer IFC_2)
    IfcBuilding -> IfcBuilding (writer IFC_2)
    IfcBuildingElementProxy -> IfcBuildingElementProxy (writer IFC_2)
    IfcBuildingStorey -> IfcBuildingStorey (writer IFC_2)
    IfcColumn -> IfcColumn (writer IFC_2)
    IfcCovering -> IfcCovering (writer IFC_2)
    IfcCurtainWall -> IfcCurtainWall (writer IFC_2)
    IfcDoor -> IfcDoor (writer IFC_2)
    IfcFlowSegment -> IfcFlowSegment (writer IFC_2)
    IfcFlowTerminal -> IfcFlowTerminal (writer IFC_2)
    IfcFurnishingElement -> IfcFurnishingElement (writer IFC_2)
    IfcMember -> IfcMember (writer IFC_2)
    IfcOpeningElement -> IfcOpeningElement (writer IFC_2)
    IfcPlate -> IfcPlate (writer IFC_2)
    IfcProject -> IfcProject (writer IFC_2)
    IfcRailing -> IfcRailing (writer IFC_2)
    IfcRoof -> IfcRoof (writer IFC_2)
    IfcSlab -> IfcSlab (writer IFC_2)
    IfcStair -> IfcStair (writer IFC_2)
    IfcStairFlight -> IfcStairFlight (writer IFC_2)
    IfcWall -> IfcWall (writer IFC_2)
    IfcWallStandardCase -> IfcWallStandardCase (writer IFC_2)
    IfcWindow -> IfcWindow (writer IFC_2)
    IfcTypeObject -> IfcTypeObject (writer IFC_2)
    QuantitySetDefinition -> QuantitySetDefinition (writer IFC_2)
    PropertySetDefinition -> PropertySetDefinition (writer IFC_2)
IfcPlate (writer IFC_2)
    attributes: GlobalId char(22), Name enumeration, Description enumeration, ObjectType enumeration, Tag enumeration, Axis enumeration, Body enumeration, Box enumeration, FootPrint enumeration
IfcBeam (writer IFC_2)
    attributes: GlobalId char(22), Name enumeration, Description enumeration, ObjectType enumeration, Tag enumeration, Axis enumeration, Body enumeration, Box enumeration, FootPrint enumeration
IfcProject (writer IFC_2)
    attributes: GlobalId char(22), Name enumeration, Description enumeration, ObjectType enumeration, LongName enumeration, Phase enumeration, Axis enumeration, Body enumeration, Box enumeration, FootPrint enumeration
IfcBuilding (writer IFC_2)
    attributes: GlobalId char(22), Name enumeration, Description enumeration, ObjectType enumeration, LongName enumeration, CompositionType enumeration, ElevationOfRefHeight number, ElevationOfTerrain number, BuildingAddress.Purpose enumeration, BuildingAddress.Description enumeration, BuildingAddress.UserDefinedPurpose enumeration, BuildingAddress.InternalLocation enumeration, BuildingAddress.AddressLines enumeration, BuildingAddress.PostalBox enumeration, BuildingAddress.Town enumeration, BuildingAddress.Region enumeration, BuildingAddress.PostalCode enumeration, BuildingAddress.Country enumeration, Axis enumeration, Body enumeration, Box enumeration, FootPrint enumeration
IfcRailing (writer IFC_2)
    attributes: GlobalId char(22), Name enumeration, Description enumeration, ObjectType enumeration, Tag enumeration, PredefinedType enumeration, Axis enumeration, Body enumeration, Box enumeration, FootPrint enumeration
IfcBuildingElementProxy (writer IFC_2)
    attributes: GlobalId char(22), Name enumeration, Description enumeration, ObjectType enumeration, Tag enumeration, CompositionType enumeration, Axis enumeration, Body enumeration, Box enumeration, FootPrint enumeration
IfcRoof (writer IFC_2)
    attributes: GlobalId char(22), Name enumeration, Description enumeration, ObjectType enumeration, Tag enumeration, ShapeType enumeration, Axis enumeration, Body enumeration, Box enumeration, FootPrint enumeration
IfcBuildingStorey (writer IFC_2)
    attributes: GlobalId char(22), Name enumeration, Description enumeration, ObjectType enumeration, LongName enumeration, CompositionType enumeration, Elevation number, Axis enumeration, Body enumeration, Box enumeration, FootPrint enumeration
IfcSlab (writer IFC_2)
    attributes: GlobalId char(22), Name enumeration, Description enumeration, ObjectType enumeration, Tag enumeration, PredefinedType enumeration, Axis enumeration, Body enumeration, Box enumeration, FootPrint enumeration
IfcColumn (writer IFC_2)
    attributes: GlobalId char(22), Name enumeration, Description enumeration, ObjectType enumeration, Tag enumeration, Axis enumeration, Body enumeration, Box enumeration, FootPrint enumeration
IfcStair (writer IFC_2)
    attributes: GlobalId char(22), Name enumeration, Description enumeration, ObjectType enumeration, Tag enumeration, ShapeType enumeration, Axis enumeration, Body enumeration, Box enumeration, FootPrint enumeration
IfcCovering (writer IFC_2)
    attributes: GlobalId char(22), Name enumeration, Description enumeration, ObjectType enumeration, Tag enumeration, PredefinedType enumeration, Axis enumeration, Body enumeration, Box enumeration, FootPrint enumeration
IfcStairFlight (writer IFC_2)
    attributes: GlobalId char(22), Name enumeration, Description enumeration, ObjectType enumeration, Tag enumeration, NumberOfRiser int, NumberOfTreads int, RiserHeight number, TreadLength number, Axis enumeration, Body enumeration, Box enumeration, FootPrint enumeration
IfcCurtainWall (writer IFC_2)
    attributes: GlobalId char(22), Name enumeration, Description enumeration, ObjectType enumeration, Tag enumeration, Axis enumeration, Body enumeration, Box enumeration, FootPrint enumeration
IfcTypeObject (writer IFC_2)
    attributes: ifc_type_name enumeration, GlobalId char(22), Name enumeration, Description enumeration, ApplicableOccurrence enumeration, Tag enumeration, ElementType enumeration, PredefinedType enumeration
IfcDoor (writer IFC_2)
    attributes: GlobalId char(22), Name enumeration, Description enumeration, ObjectType enumeration, Tag enumeration, OverallHeight number, OverallWidth number, Axis enumeration, Body enumeration, Box enumeration, FootPrint enumeration
IfcWall (writer IFC_2)
    attributes: GlobalId char(22), Name enumeration, Description enumeration, ObjectType enumeration, Tag enumeration, Axis enumeration, Body enumeration, Box enumeration, FootPrint enumeration
IfcFlowSegment (writer IFC_2)
    attributes: GlobalId char(22), Name enumeration, Description enumeration, ObjectType enumeration, Tag enumeration, Axis enumeration, Body enumeration, Box enumeration, FootPrint enumeration
IfcWallStandardCase (writer IFC_2)
    attributes: GlobalId char(22), Name enumeration, Description enumeration, ObjectType enumeration, Tag enumeration, Axis enumeration, Body enumeration, Box enumeration, FootPrint enumeration
IfcFlowTerminal (writer IFC_2)
    attributes: GlobalId char(22), Name enumeration, Description enumeration, ObjectType enumeration, Tag enumeration, Axis enumeration, Body enumeration, Box enumeration, FootPrint enumeration
IfcWindow (writer IFC_2)
    attributes: GlobalId char(22), Name enumeration, Description enumeration, ObjectType enumeration, Tag enumeration, OverallHeight number, OverallWidth number, Axis enumeration, Body enumeration, Box enumeration, FootPrint enumeration
IfcFurnishingElement (writer IFC_2)
    attributes: GlobalId char(22), Name enumeration, Description enumeration, ObjectType enumeration, Tag enumeration, Axis enumeration, Body enumeration, Box enumeration, FootPrint enumeration
PropertySetDefinition (writer IFC_2)
IfcMember (writer IFC_2)
    attributes: GlobalId char(22), Name enumeration, Description enumeration, ObjectType enumeration, Tag enumeration, Axis enumeration, Body enumeration, Box enumeration, FootPrint enumeration
QuantitySetDefinition (writer IFC_2)
IfcOpeningElement (writer IFC_2)
    attributes: GlobalId char(22), Name enumeration, Description enumeration, ObjectType enumeration, Tag enumeration, Axis enumeration, Body enumeration, Box enumeration, FootPrint enumeration
IfcSite (writer IFC_2)
    attributes: GlobalId char(22), Name enumeration, Description enumeration, ObjectType enumeration, LongName enumeration, CompositionType enumeration, RefLatitude number, RefLongitude number, RefElevation number, LandTitleNumber enumeration, SiteAddress.Purpose enumeration, SiteAddress.Description enumeration, SiteAddress.UserDefinedPurpose enumeration, SiteAddress.InternalLocation enumeration, SiteAddress.AddressLines enumeration, SiteAddress.PostalBox enumeration, SiteAddress.Town enumeration, SiteAddress.Region enumeration, SiteAddress.PostalCode enumeration, SiteAddress.Country enumeration, Axis enumeration, Body enumeration, Box enumeration, FootPrint enumeration

Bookmark: Set IfcSite CRS and Recalcuate RefLongitude and RefLatitude
GeometryExtractor
    ATTR = _geometry
    ELLIPSOID_NAME = WGS84
    GEOHASH_PRECISION_DISPLAY = ~9.3 mm (12 characters)
    ISO6709_FORMAT_CHOICE = Degrees and Decimal Degrees
    ISO6709_MAX_DECIMAL_PLACES = 5
    JSON_MAX_DIGITS = 7
    KIND_LONG = FME Binary
    LETTERING = WGS84
    LEVELS_ATTR = _levels
    MSSQL_FORMAT_CHOICE = Geometry
    OGCVERSION = 1.2
    OGC_WKT_PRECISION_DISPLAY = 64-bit
    OGEOSMS_URL_PREFIX = http://maps.google.com/?q=
    OMIT_NAMESPACES_DISPLAY = No
    PRECISION = 0
    PREFER_POLYGON_OVER_SURFACE = No
    REMOVE_GEOMETRY = No
    -> CoordinateSystemExtractor_2
CoordinateSystemExtractor_2
    CRDSYS_ATTR = _coordsys0
    -> Deaggregator
Deaggregator
    EXPLODE_INSTANCES = No
    GEOM_NAME_FIELD = _geometry_name
    LIST_ATTR_MODE_LOOKUP = LEAN
    MODE = Flatten All Levels
    SPLIT_COMPOSITES = No
    DEAGGREGATED -> BoundingBoxAccumulator
BoundingBoxAccumulator
    ACCUM_ATTRS_NAME = Use Attributes From One Feature
    BOUNDING_BOX -> CommonLocalReprojector
Note: CommonLocalReprojector [CommonLocalReprojector] / Transformer: / Group By Mode: Process At End (Blocking) / Parameters: / Projection Type: Equidistant (AZMED) / Vertical Handling: Ignore heights and leave them unchanged
CommonLocalReprojector
    PROJECTION_TYPE = Equidistant (AZMED)
    VERTICAL_HANDLING = Ignore heights and leave them unchanged
    -> CoordinateSystemExtractor
CoordinateSystemExtractor
    CRDSYS_ATTR = _coordsys
    -> GeometryReplacer
GeometryReplacer
    ELLIPSOID_NAME = WGS84
    KIND_LONG = FME Binary
    LETTERING = WGS84
    MSSQL_FORMAT_CHOICE = Geometry
    OGC_WKT_PRECISION_DISPLAY = 64-bit
    OUTPUT_POINT_DISPLAY = Point
    REMOVE_ATTRIBUTE = Yes
    SOURCE = @Value(_geometry)
    SRS_AXIS_ORDER_DISPLAY = Automatic
    -> AttributeSplitter
AttributeSplitter
    ATTR_NAME = _coordsys
    DELIMITER = _
    DROP_EMPTY_PARTS = No
    LIST_NAME = _list
    TRIM_OPTION = Both
    -> AttributeCreator_6
Note: AttributeCreator_6 [AttributeCreator] / Attributes To Create: New AttributeAttribute ValueRefLongitude@Value(_list{3})RefLatitude@Value(_list{4})RefElevation0
AttributeCreator_6
    ATTR_TABLE:
      SET_TO RefLongitude = @Value(_list{3})
      SET_TO RefLatitude = @Value(_list{4})
      SET_TO RefElevation = 0
    -> FeatureMerger [SUPPLIER]
FeatureMerger
    ATTR_ACCUM_MODE = Prefix Supplier
    IGNORE_NULLS = No
    JOIN_KEYS = 1 1 AUTO
    MERGE_TYPE = Attributes Only
    PROCESS_DUPS = NO
    REJECT_NULL_MISSING_KEYS = No
    SUPPLIERS_FIRST = No
    SUPPLIER_PREFIX = crs_
    MERGED -> AttributeCopier
AttributeCopier
    ATTR_TABLE:
      COPY crs_RefLongitude > RefLongitude
      COPY crs_RefLatitude > RefLatitude
      COPY crs_RefElevation > RefElevation
    -> GeometryPropertySetter
GeometryPropertySetter
    GQUERY:
      for $geom in //geometry
      where $geom/count(parent::geometry) = 0
      return number($geom/@fme_id)
    OVERWRITE_CHOICE = Yes
    REMOVE_ATTRIBUTE = No
    SETTYPE_PARAM = Traits From Attributes
    SRC_ATTRS = RefElevation RefLatitude RefLongitude
    SET -> IfcSite (writer IFC_2)
