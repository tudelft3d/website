FME workspace Myran_georeference.fmw

Parameters:
- SourceDataset_TEXTLINE_5 = C:\Users\jtekavec\Desktop\Benchmark\Myran\Spremenjeno\Myran_fixed_manual.ifc   # Source Text File(s)
- SourceDataset_TEXTLINE = $(FME_MF_DIR)Myran_fixed.ifc   # Source Text File(s)
- DestDataset_TEXTLINE = $(FME_MF_DIR)Myran_georeferenced.ifc   # Destination Text File
- rotation = 0.
- shiftX = 145312832.
- shiftY = 6721748645.
- shiftZ = 340500.

Readers:
- TEXTLINE_1: TEXTLINE from $(SourceDataset_TEXTLINE_5)
- TEXTLINE_2: TEXTLINE from $(SourceDataset_TEXTLINE)

Writers:
- TEXTLINE_3: TEXTLINE to $(DestDataset_TEXTLINE)

text_line (reader TEXTLINE_2)
    attributes: text_line_data buffer
    -> Tester
    -> FeatureMerger_4 [REQUESTOR]
    -> FeatureMerger_6 [REQUESTOR]
    -> Tester_3
AttributeSplitter
    ATTR_NAME = text_line_data
    DELIMITER = ,
    DROP_EMPTY_PARTS = No
    LIST_NAME = _list
    TRIM_OPTION = Both
    -> AttributeCreator
AttributeCreator
    ATTR_TABLE = SET_TO local_placement = @Value(_list{5})
    -> FeatureMerger [SUPPLIER]
FeatureMerger_4
    ATTR_ACCUM_MODE = Merge Supplier
    ATTR_CONFLICT_RES = Use Supplier
    IGNORE_NULLS = No
    JOIN_KEYS = @Value(text_line_number) @Value(text_line_number) AUTO
    MERGE_TYPE = Attributes Only
    PROCESS_DUPS = NO
    REJECT_NULL_MISSING_KEYS = No
    SUPPLIERS_FIRST = No
    MERGED -> text_line (writer TEXTLINE_3)
    UNMERGED_REQUESTOR -> text_line (writer TEXTLINE_3)
text_line (writer TEXTLINE_3)
    attributes: text_line_data buffer

Bookmark: Get the row number of the last line of data (suspecting it has the highest number)
Tester_3
    BOOL_OP = OR
    TEST_CLAUSE = CASE_INSENSITIVE_TEST @Value(text_line_data) CONTAINS ENDSEC
    PASSED -> Sampler
Sampler
    RATE = 1
    SAMPLE_MODE = No
    SAMPLE_TYPE_LONG = Last N Features
    SAMPLED -> FeatureMerger_6 [SUPPLIER]
FeatureMerger_6
    ATTR_ACCUM_MODE = Merge Supplier
    ATTR_CONFLICT_RES = Use Requestor
    IGNORE_NULLS = No
    JOIN_KEYS = @Value(text_line_number) @Evaluate(@Value(text_line_number)-1) AUTO
    MERGE_TYPE = Attributes Only
    PROCESS_DUPS = NO
    REJECT_NULL_MISSING_KEYS = No
    SUPPLIERS_FIRST = No
    MERGED -> AttributeManager_3
AttributeManager_3
    ATTR_TABLE = SET_TO text_line_data > last_number = @Substring(@Value(text_line_data),1,@FindString(@Value(text_line_data),"=")-1)
    -> FeatureMerger_7 [SUPPLIER]
    -> FeatureMerger_8 [SUPPLIER]
    -> FeatureMerger_9 [SUPPLIER]

Bookmark: Find IFCSITE
Tester
    BOOL_OP = OR
    TEST_CLAUSE = CASE_INSENSITIVE_TEST @Value(text_line_data) CONTAINS IFCSITE
    PASSED -> AttributeSplitter
    FAILED -> FeatureMerger [REQUESTOR]
    FAILED -> FeatureMerger_2 [REQUESTOR]
    FAILED -> FeatureMerger_3 [REQUESTOR]
    FAILED -> FeatureMerger_5 [REQUESTOR]

Bookmark: Find IFCAXIS2PLACEMENT3D
FeatureMerger
    ATTR_ACCUM_MODE = Merge Supplier
    ATTR_CONFLICT_RES = Use Requestor
    IGNORE_NULLS = No
    JOIN_KEYS = @Substring(@Value(text_line_data),0,@FindString(@Value(text_line_data),=)) @Value(local_placement) AUTO
    MERGE_TYPE = Attributes Only
    PROCESS_DUPS = NO
    REJECT_NULL_MISSING_KEYS = No
    SUPPLIERS_FIRST = No
    MERGED -> AttributeSplitter_2
AttributeSplitter_2
    ATTR_NAME = text_line_data
    DELIMITER = ,
    DROP_EMPTY_PARTS = No
    LIST_NAME = _list2
    TRIM_OPTION = Both
    -> AttributeCreator_2
AttributeCreator_2
    ATTR_TABLE = SET_TO axis2placement3D = @Substring(@Value(_list2{1}),0,@FindString(@Value(_list2{1}),")"))
    -> FeatureMerger_2 [SUPPLIER]

Bookmark: Find IFCCARTESIANPOINT and IFCDIRECTION
FeatureMerger_2
    ATTR_ACCUM_MODE = Merge Supplier
    ATTR_CONFLICT_RES = Use Requestor
    IGNORE_NULLS = No
    JOIN_KEYS = @Substring(@Value(text_line_data),0,@FindString(@Value(text_line_data),"=")) @Value(axis2placement3D) AUTO
    MERGE_TYPE = Attributes Only
    PROCESS_DUPS = NO
    REJECT_NULL_MISSING_KEYS = No
    SUPPLIERS_FIRST = No
    MERGED -> AttributeSplitter_3
AttributeSplitter_3
    ATTR_NAME = text_line_data
    DELIMITER = ,
    DROP_EMPTY_PARTS = No
    LIST_NAME = _list3
    TRIM_OPTION = Both
    -> AttributeCreator_3
AttributeCreator_3
    ATTR_TABLE:
      SET_TO CartesianPoint = @Substring(@Value(_list3{0}),@Evaluate(@FindString(@Value(_list3{0}),"(#"))+1)
      SET_TO DirectionZ = @Substring(@Value(_list3{2}),0,@FindString(@Value(_list3{2}),")"))
      SET_TO DirectionX = @Value(_list3{1})
    -> TestFilter_2

Bookmark: Check for unset values
TestFilter_2
    DEFAULT_VALUE = none
    TEST_LIST:
      "BOOL_OP,AND,COMPOSITE_TEST,""""""<Unused>"""""",TEST_CLAUSE,TEST @Value(CartesianPoint) = $
      TEST @Value(DirectionZ) = $",both,"BOOL_OP,AND,COMPOSITE_TEST,""""""<Unused>"""""",TEST_CLAUSE,TEST @Value(CartesianPoint) = $
      TEST @Value(DirectionZ) != $",point,"BOOL_OP,AND,COMPOSITE_TEST,""""""<Unused>"""""",TEST_CLAUSE,TEST @Value(DirectionZ) = $
      TEST @Value(CartesianPoint) != $",direction
    both -> FeatureMerger_7 [REQUESTOR]
    point -> FeatureMerger_5 [SUPPLIER]
    point -> FeatureMerger_8 [REQUESTOR]
    direction -> FeatureMerger_3 [SUPPLIER]
    direction -> FeatureMerger_9 [REQUESTOR]
    none -> FeatureMerger_3 [SUPPLIER]
    none -> FeatureMerger_5 [SUPPLIER]

Bookmark: Adds new references to georeferenced direction and point
FeatureMerger_7
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> AttributeManager_4
AttributeManager_4
    ATTR_TABLE:
      SET_TO text_line_data = @Value(axis2placement3D)= IFCAXIS2PLACEMENT3D(#@Evaluate(@Value(last_number)+1),@Value(DirectionX),#@Evaluate(@Value(last_number)+2));
        #@Evaluate(@Value(last_number)+1)= IFCCARTESIANPOINT(($(shiftX),$(shiftY),$(shiftZ)));
        #@Evaluate(@Value(last_number)+2)= IFCDIRECTION((@cos(@degToRad(-$(rotation))),@sin(@degToRad(-$(rotation))),0.));
    -> FeatureMerger_4 [SUPPLIER]
FeatureMerger_8
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> AttributeManager_5
AttributeManager_5
    ATTR_TABLE:
      SET_TO text_line_data = @Value(axis2placement3D)= IFCAXIS2PLACEMENT3D(#@Evaluate(@Value(last_number)+1),@Value(DirectionX),@Value(DirectionZ));
        #@Evaluate(@Value(last_number)+1)= IFCCARTESIANPOINT(($(shiftX),$(shiftY),$(shiftZ)));
    -> FeatureMerger_4 [SUPPLIER]
FeatureMerger_9
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> AttributeManager_6
AttributeManager_6
    ATTR_TABLE:
      SET_TO text_line_data = @Value(axis2placement3D)= IFCAXIS2PLACEMENT3D(@Value(CartesianPoint),@Value(DirectionX),#@Evaluate(@Value(last_number)+1));
        #@Evaluate(@Value(last_number)+1)= IFCDIRECTION((@cos(@degToRad(-$(rotation))),@sin(@degToRad(-$(rotation))),0.));
    -> FeatureMerger_4 [SUPPLIER]

Bookmark: Search for point and direction
FeatureMerger_3
    ATTR_ACCUM_MODE = Merge Supplier
    ATTR_CONFLICT_RES = Use Requestor
    IGNORE_NULLS = No
    JOIN_KEYS = @Substring(@Value(text_line_data),0,@FindString(@Value(text_line_data),"=")) @Value(CartesianPoint) AUTO
    MERGE_TYPE = Attributes Only
    PROCESS_DUPS = NO
    REJECT_NULL_MISSING_KEYS = No
    SUPPLIERS_FIRST = No
    MERGED -> AttributeManager
AttributeManager
    ATTR_TABLE = SET_TO text_line_data = @Substring(@Value(text_line_data),0,@FindString(@Value(text_line_data),"(("))(($(shiftX),$(shiftY),$(shiftZ)));
    -> FeatureMerger_4 [SUPPLIER]
FeatureMerger_5
    ATTR_ACCUM_MODE = Merge Supplier
    ATTR_CONFLICT_RES = Use Requestor
    IGNORE_NULLS = No
    JOIN_KEYS = @Substring(@Value(text_line_data),0,@FindString(@Value(text_line_data),"=")) @Value(DirectionZ) AUTO
    MERGE_TYPE = Attributes Only
    PROCESS_DUPS = NO
    REJECT_NULL_MISSING_KEYS = No
    SUPPLIERS_FIRST = No
    MERGED -> AttributeManager_2
AttributeManager_2
    ATTR_TABLE = SET_TO text_line_data = @Substring(@Value(text_line_data),0,@FindString(@Value(text_line_data),"(("))((@cos(@degToRad(-$(rotation))),@sin(@degToRad(-$(rotation))),0.)));
    -> FeatureMerger_4 [SUPPLIER]
