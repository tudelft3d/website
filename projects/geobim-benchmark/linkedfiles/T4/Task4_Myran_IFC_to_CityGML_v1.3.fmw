FME workspace Task4_Myran_IFC_to_CityGML_v1.3.fmw
Title: Myran_IFC_to_CityGML
Description: Myran_IFC_to_CityGML
Convert from Myran building dataset in IFC 2x3 to CityGML 2.0 LOD4
History: 2019/11/13,Jovita,Created,2019/11/15,Dean Hintz,Modifications to ConvertGeometry to clean surfaces, correct orientation and fix crash,2019/11/22,Dean Hintz,Added GroundSurface. Modifications to support validation - prefixed gml_ids with alpha character (ID_),2019/11/24,Dean Hintz,Removed unnecessary user defined fields,2019/11/25,Dean Hintz,Added IFC georeferencing (previously done as a 2nd step). Established correct hierarchy. Ensured full validation with CityGML 2.0

Parameters:
- SourceDataset_IFC = C:\Users\dhintz\Dropbox (Safe Software Inc.)\DeanSafe\Projects\_StrategicProjects\GeoBIM\testData_ifc\Myran_fixed.ifc   # Source Industry Foundation Class (IFC) File(s)
- SourceDataset_IFC_5 = C:\Users\dhintz\Dropbox (Safe Software Inc.)\DeanSafe\Projects\_StrategicProjects\GeoBIM\testData_ifc\Myran_fixed.ifc   # Source Industry Foundation Class (IFC) File(s)
- FEATURE_TYPES =   # Feature Types to Read
- DestDataset_CITYGML = C:\Users\dhintz\Dropbox (Safe Software Inc.)\DeanSafe\Projects\_StrategicProjects\GeoBIM\Task4_Conversion\output\Myran-CityGML-LOD4_safe_v1.3.gml   # Destination CityGML Document
- COORDSYS = EPSG:3013   # COORDSYS Coordinate System
- PRETTY_PRINT_CITYGML = No   # Pretty Print
- CITYGML_VALIDATION_CITYGML = Yes   # Validate Output File
- CityModelID = ID_Myran_dataset_fromIFC_101   # CityModel ID
- BuildingID = ID_Myran_building_fromIFC_101   # Building ID

Readers:
- IFC_1: IFC from $(SourceDataset_IFC_5)
- IFC_2: IFC from $(SourceDataset_IFC)

Writers:
- CITYGML_1: CITYGML to $(DestDataset_CITYGML) in $(COORDSYS)

CoordinateSystemRemover
    -> Scaler
Note: Scaler [Scaler] / Scale Factors: / X: 0.001 / Y: 0.001 / Z: 0.001 / Parameters: / Text Scaling: Location and Size / Raster Scaling: Extents / Scale Origin: 0,0 / Point Cloud: / Point Cloud Components to Scale: <not set>
Scaler
    RASTER_SCALING = Extents
    SCALE_ORIGIN = 0,0
    TEXT_LOC_ONLY = Location and Size
    XSCALE = 0.001
    YSCALE = 0.001
    ZSCALE = 0.001
    SCALED -> Offsetter
    <REJECTED> -> CoordinateSystemSetter
Note: Offsetter [Offsetter] / Parameters: / Mode: Cartesian Coordinate / Cartesian Coordinate Parameters: / X Offset: 145312.8320 / Y Offset: 6721748.645 / Z Offset: 340.5 / Point Cloud: / Point Cloud Components to Offset: <not set>
Offsetter
    MODE = Cartesian Coordinate
    XOFF = 145312.8320
    YOFF = 6721748.645
    ZOFF = 340.5
    OFFSET -> CoordinateSystemSetter
    <REJECTED> -> CoordinateSystemSetter
Note: CoordinateSystemSetter [CoordinateSystemSetter] / Parameters: / Coordinate System: $(COORDSYS)
CoordinateSystemSetter
    COORDSYS = $(COORDSYS)
    -> FeatureTypeFilter
FeatureTypeFilter
    ATTRIBUTES = <Blank>,<Unfiltered>,GroundSurface,Window,IntBuildingInstallation,BuildingFurniture,Door,RoofSurface,FloorSurface,BuildingInstallation,WallSurface
    WallSurface -> WallSurface (writer CITYGML_1)
    WallSurface -> FeatureTypeFilter_WallSurface
    FloorSurface -> FloorSurface (writer CITYGML_1)
    RoofSurface -> RoofSurface (writer CITYGML_1)
    GroundSurface -> GroundSurface (writer CITYGML_1)
    Window -> Window (writer CITYGML_1)
    IntBuildingInstallation -> IntBuildingInstallation (writer CITYGML_1)
    BuildingFurniture -> BuildingFurniture (writer CITYGML_1)
    Door -> Door (writer CITYGML_1)
    Door -> FeatureTypeFilter_Door
    BuildingInstallation -> BuildingInstallation (writer CITYGML_1)
FeatureTypeFilter_Door: Inspector
GroundSurface (writer CITYGML_1)
    attributes: gml_description xml_buffer, gml_name xml_buffer, citygml_feature_role xml_buffer, citygml_target_uri xml_buffer, citygml_feature_role_attr_name xml_buffer, citygml_feature_role_attr_val xml_buffer, citygml_creationDate xml_buffer, citygml_terminationDate xml_buffer, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer, GlobalId xml_buffer, Name xml_buffer
Window (writer CITYGML_1)
    attributes: citygml_target_uri xml_buffer, citygml_feature_role xml_buffer, citygml_feature_role_attr_name xml_buffer, citygml_feature_role_attr_val xml_buffer, gml_description xml_buffer, gml_name xml_buffer, citygml_creationDate xml_buffer, citygml_terminationDate xml_buffer, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, GlobalId xml_buffer, Name xml_buffer
IntBuildingInstallation (writer CITYGML_1)
    attributes: citygml_target_uri xml_buffer, citygml_feature_role xml_buffer, citygml_feature_role_attr_name xml_buffer, citygml_feature_role_attr_val xml_buffer, gml_description xml_buffer, gml_name xml_buffer, citygml_creationDate xml_buffer, citygml_terminationDate xml_buffer, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_level_of_detail{} xml_buffer, citygml_bounded_by{}.xlink_href xml_buffer, GlobalId xml_buffer, Name xml_buffer
BuildingFurniture (writer CITYGML_1)
    attributes: citygml_target_uri xml_buffer, citygml_feature_role xml_buffer, citygml_feature_role_attr_name xml_buffer, citygml_feature_role_attr_val xml_buffer, gml_description xml_buffer, gml_name xml_buffer, citygml_creationDate xml_buffer, citygml_terminationDate xml_buffer, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_level_of_detail{} xml_buffer, GlobalId xml_buffer, Name xml_buffer
Door (writer CITYGML_1)
    attributes: citygml_target_uri xml_buffer, citygml_feature_role xml_buffer, citygml_feature_role_attr_name xml_buffer, citygml_feature_role_attr_val xml_buffer, gml_description xml_buffer, gml_name xml_buffer, citygml_creationDate xml_buffer, citygml_terminationDate xml_buffer, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_address{}.xlink_href xml_buffer, GlobalId xml_buffer, Name xml_buffer
RoofSurface (writer CITYGML_1)
    attributes: gml_description xml_buffer, gml_name xml_buffer, citygml_feature_role xml_buffer, citygml_target_uri xml_buffer, citygml_feature_role_attr_name xml_buffer, citygml_feature_role_attr_val xml_buffer, citygml_creationDate xml_buffer, citygml_terminationDate xml_buffer, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer, GlobalId xml_buffer, Name xml_buffer
FloorSurface (writer CITYGML_1)
    attributes: gml_description xml_buffer, gml_name xml_buffer, citygml_feature_role xml_buffer, citygml_target_uri xml_buffer, citygml_feature_role_attr_name xml_buffer, citygml_feature_role_attr_val xml_buffer, citygml_creationDate xml_buffer, citygml_terminationDate xml_buffer, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer, GlobalId xml_buffer, Name xml_buffer
BuildingInstallation (writer CITYGML_1)
    attributes: citygml_target_uri xml_buffer, citygml_feature_role xml_buffer, citygml_feature_role_attr_name xml_buffer, citygml_feature_role_attr_val xml_buffer, gml_description xml_buffer, gml_name xml_buffer, citygml_creationDate xml_buffer, citygml_terminationDate xml_buffer, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_level_of_detail{} xml_buffer, citygml_bounded_by{}.xlink_href xml_buffer, GlobalId xml_buffer, Name xml_buffer
WallSurface (writer CITYGML_1)
    attributes: gml_description xml_buffer, gml_name xml_buffer, citygml_feature_role xml_buffer, citygml_target_uri xml_buffer, citygml_feature_role_attr_name xml_buffer, citygml_feature_role_attr_val xml_buffer, citygml_creationDate xml_buffer, citygml_terminationDate xml_buffer, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer, GlobalId xml_buffer, Name xml_buffer
FeatureTypeFilter_WallSurface: Inspector

Bookmark: Unneeded
IfcBuildingStorey (reader IFC_2) [off]
    attributes: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
IfcOpeningElement (reader IFC_2) [off]
    attributes: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
PropertySetDefinition (reader IFC_2) [off]
    attributes: ifc_properties{}.property_type string, ifc_properties{}.data_type string, ifc_properties{}.name string, ifc_property_set_name string
QuantitySetDefinition (reader IFC_2) [off]
    attributes: ifc_quantities{}.name string, ifc_quantity_set_name string, ifc_quantities{}.type string
IfcTypeObject (reader IFC_2) [off]
    attributes: ifc_type_name string, GlobalId char(22), Name string, Description string, ApplicableOccurrence string, Tag string, ElementType string, PredefinedType string
IfcCovering (reader IFC_2) [off]
    attributes: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
IfcFlowSegment (reader IFC_2) [off]
    attributes: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

Bookmark: Create Parent/Child lookup
IfcBeam (reader IFC_1)
    attributes: GlobalId char(22), Name string, Description string, ObjectType string, Tag string, Axis geometry, Body geometry, Box geometry, FootPrint geometry, SiteAddress.Region string, RefElevation real, SiteAddress.Purpose enumeration, RiserHeight real, SiteAddress.PostalCode string, ElementType string, RefLatitude real, LandTitleNumber string, RefLongitude real, SiteAddress.Town string, BuildingAddress.Purpose enumeration, NumberOfTreads int, BuildingAddress.UserDefinedPurpose string, SiteAddress.InternalLocation string, CompositionType string, BuildingAddress.PostalCode string, LongName string, BuildingAddress.Country string, ShapeType enumeration, NumberOfRiser int, BuildingAddress.Region string,
      BuildingAddress.Description string, BuildingAddress.PostalBox string, PredefinedType enumeration, ElevationOfRefHeight real, BuildingAddress.AddressLines string, Elevation real, BuildingAddress.Town string, SiteAddress.PostalBox string, OverallWidth real, Phase string, OverallHeight real, SiteAddress.Description string, TreadLength real, SiteAddress.Country string, ifc_type_name string, ifc_type_object_id string, ElevationOfTerrain real, SiteAddress.UserDefinedPurpose string, BuildingAddress.InternalLocation string, ApplicableOccurrence string, SiteAddress.AddressLines string
    -> BinaryEncoder
BinaryEncoder
    ATTRS_TO_ENCODE = ifc_unique_id
    DEST_ATTRS = _unique_id
    ENCODING_TYPE = HEX
    WRITE_TO_OTHER_ATTRS = Yes
    -> BinaryEncoder_2
BinaryEncoder_2
    ATTRS_TO_ENCODE = ifc_parent_unique_id
    DEST_ATTRS = _parent_id
    ENCODING_TYPE = HEX
    WRITE_TO_OTHER_ATTRS = Yes
    -> AttributeExposer
AttributeExposer
    ATTR_LIST = _unique_id,_parent_id
    -> VariableSetter
VariableSetter
    SCOPE = Global
    VALUE = @Value(_parent_id)
    VARNAME = p@Value(_unique_id)
    -> VariableSetter_2
VariableSetter_2
    SCOPE = Global
    VALUE = @Value(fme_feature_type)
    VARNAME = t@Value(_unique_id)

Bookmark: CityModel
IfcProject (reader IFC_2)
    attributes: GlobalId char(22), Name string, Description string, ObjectType string, LongName string, Phase string, Axis geometry, Body geometry, Box geometry, FootPrint geometry, ifc_type_object_id string
    -> GeometryRemover_2
GeometryRemover_2
    -> AttributeCreator_10
AttributeCreator_10
    ATTR_TABLE:
      SET_TO gml_id = $(CityModelID)
      SET_TO gml_description = @Value(Description)
      SET_TO gml_name = @Value(LongName)
    -> CityModel (writer CITYGML_1)
CityModel (writer CITYGML_1)
    attributes: citygml_target_uri xml_buffer, gml_description xml_buffer, gml_name xml_buffer, citygml_city_object_member{}.xlink_href xml_buffer, citygml_appearance_member{}.xlink_href xml_buffer, gml_feature_member{}.xlink_href xml_buffer, GlobalId xml_buffer, Name xml_buffer

Bookmark: Building
IfcBuilding (reader IFC_2)
    attributes: GlobalId char(22), Name string, Description string, ObjectType string, LongName string, CompositionType string, ElevationOfRefHeight real, ElevationOfTerrain real, BuildingAddress.Purpose enumeration, BuildingAddress.Description string, BuildingAddress.UserDefinedPurpose string, BuildingAddress.InternalLocation string, BuildingAddress.AddressLines string, BuildingAddress.PostalBox string, BuildingAddress.Town string, BuildingAddress.Region string, BuildingAddress.PostalCode string, BuildingAddress.Country string, Axis geometry, Body geometry, Box geometry, FootPrint geometry, ifc_type_object_id string
    -> GeometryRemover
Note: Remove geometry
GeometryRemover
    -> AttributeCreator_11
Note: Set gml_id, gml_parent_id, gml_description, defaults
AttributeCreator_11
    ATTR_TABLE:
      SET_TO gml_id = $(BuildingID)
      SET_TO gml_description = @Value(Description)
      SET_TO gml_name = @Value(LongName)
      SET_TO gml_parent_id = $(CityModelID)
      SET_TO citygml_target_uri = http://www.opengis.net/citygml/building/2.0
      SET_TO citygml_creationDate = 2019-11-15
      SET_TO citygml_feature_role = cityObjectMember
    -> Building (writer CITYGML_1)
Building (writer CITYGML_1)
    attributes: gml_description xml_buffer, gml_name xml_buffer, citygml_target_uri xml_buffer, citygml_creationDate xml_buffer, citygml_feature_role xml_buffer, citygml_feature_role_attr_name xml_buffer, citygml_feature_role_attr_val xml_buffer, citygml_terminationDate xml_buffer, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer,
      citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer, GlobalId xml_buffer, Name xml_buffer

Bookmark: GroundSurface
IfcSite (reader IFC_2)
    attributes: GlobalId char(22), Name string, Description string, ObjectType string, LongName string, CompositionType string, RefLatitude real, RefLongitude real, RefElevation real, LandTitleNumber string, SiteAddress.Purpose enumeration, SiteAddress.Description string, SiteAddress.UserDefinedPurpose string, SiteAddress.InternalLocation string, SiteAddress.AddressLines string, SiteAddress.PostalBox string, SiteAddress.Town string, SiteAddress.Region string, SiteAddress.PostalCode string, SiteAddress.Country string, Axis geometry, Body geometry, Box geometry, FootPrint geometry, ifc_type_object_id string
    -> ConvertGeometry_10
Note: Convert Geometry to / simple surface
ConvertGeometry_10
    IFC_UNIQUE_ID = @Value(ifc_unique_id)
    -> BinaryEncoder_11
Note: Get parent type
BinaryEncoder_11
    ATTRS_TO_ENCODE = ifc_parent_unique_id
    DEST_ATTRS = _parent_id
    ENCODING_TYPE = HEX
    WRITE_TO_OTHER_ATTRS = Yes
    -> AttributeExposer_11
AttributeExposer_11
    ATTR_LIST = _parent_id
    -> VariableRetriever_10
VariableRetriever_10
    SCOPE = Global
    VALUE_ATTR = _parent_type
    VARNAME = t@Value(_parent_id)
    -> AttributeRenamer_5
Note: Set gml id
AttributeRenamer_5
    ATTR_TABLE:
      RENAME_SET_DEFAULT ifc_parent_unique_id > gml_parent_id
      RENAME_SET_DEFAULT ifc_unique_id > gml_id
    -> GetGrandParentID_8
Note: Set parent id
GetGrandParentID_8
    ATTR_TO_ENCODE = gml_parent_id
    DEST_ATTR = gml_parent_id
    -> CityGMLGeometrySetter_2
Note: Set LOD and role
CityGMLGeometrySetter_2
    GEOM = lod2MultiSurface
    ROLE = boundedBy
    -> CityGMLattributeRefiner_9
CityGMLattributeRefiner_9
    DESCRIPTION = @Value(Description)
    GML_ID = @Value(gml_id)
    GML_PARENT_ID = @Value(gml_parent_id)
    -> AttributeCreator
AttributeCreator
    ATTR_TABLE:
      SET_TO fme_feature_type = GroundSurface
      SET_TO gml_parent_id = $(BuildingID)
    -> CoordinateSystemRemover

Bookmark: Window
IfcPlate (reader IFC_2)
    attributes: GlobalId char(22), Name string, Description string, ObjectType string, Tag string, Axis geometry, Body geometry, Box geometry, FootPrint geometry, ifc_type_object_id string
    -> ConvertGeometry_2
Note: Convert Geometry to / simple surface
ConvertGeometry_2
    IFC_UNIQUE_ID = @Value(ifc_unique_id)
    -> AttributeRenamer
Note: Set gml id
AttributeRenamer
    ATTR_TABLE:
      RENAME_SET_DEFAULT ifc_unique_id > gml_id
      RENAME_SET_DEFAULT ifc_parent_unique_id > gml_parent_id
    -> CityGMLattributeRefiner_10
CityGMLattributeRefiner_10
    DESCRIPTION = @Value(Description)
    GML_ID = @Value(gml_id)
    GML_PARENT_ID = @Value(gml_parent_id)
    -> AttributeCreator_12
AttributeCreator_12
    ATTR_TABLE = SET_TO gml_parent_id = $(BuildingID)
    -> CityGMLGeometrySetter_7
IfcWindow (reader IFC_2)
    attributes: GlobalId char(22), Name string, Description string, ObjectType string, Tag string, OverallHeight real, OverallWidth real, Axis geometry, Body geometry, Box geometry, FootPrint geometry, ifc_type_object_id string
    -> ConvertGeometry_4
ConvertGeometry_4
    IFC_UNIQUE_ID = @Value(ifc_unique_id)
    -> AttributeRenamer_2
AttributeRenamer_2
    ATTR_TABLE = RENAME_SET_DEFAULT ifc_unique_id > gml_id
    -> GetGrandParentID_2
Note: Set parent id
GetGrandParentID_2
    ATTR_TO_ENCODE = ifc_parent_unique_id
    DEST_ATTR = gml_parent_id
    -> CityGMLattributeRefiner_8
CityGMLattributeRefiner_8
    DESCRIPTION = @Value(Description)
    GML_ID = @Value(gml_id)
    GML_PARENT_ID = @Value(gml_parent_id)
    -> CityGMLGeometrySetter_7
Note: Set LOD and role
CityGMLGeometrySetter_7
    GEOM = lod4MultiSurface
    ROLE = opening
    -> AttributeCreator_2
AttributeCreator_2
    ATTR_TABLE = SET_TO fme_feature_type = Window
    -> CoordinateSystemRemover

Bookmark: IntBuildingInstallation
IfcFlowTerminal (reader IFC_2)
    attributes: GlobalId char(22), Name string, Description string, ObjectType string, Tag string, Axis geometry, Body geometry, Box geometry, FootPrint geometry, ifc_type_object_id string
    -> ConvertGeometry_12
Note: Convert Geometry to / simple surface
ConvertGeometry_12
    IFC_UNIQUE_ID = @Value(ifc_unique_id)
    -> BinaryEncoder_10
Note: Get parent type
BinaryEncoder_10
    ATTRS_TO_ENCODE = ifc_parent_unique_id
    DEST_ATTRS = _parent_id
    ENCODING_TYPE = HEX
    WRITE_TO_OTHER_ATTRS = Yes
    -> AttributeExposer_9
AttributeExposer_9
    ATTR_LIST = _parent_id
    -> VariableRetriever_9
VariableRetriever_9
    SCOPE = Global
    VALUE_ATTR = _parent_type
    VARNAME = t@Value(_parent_id)
    -> AttributeRenamer_10
Note: Set gml id
AttributeRenamer_10
    ATTR_TABLE:
      RENAME_SET_DEFAULT ifc_parent_unique_id > gml_parent_id
      RENAME_SET_DEFAULT ifc_unique_id > gml_id
    -> Tester_7
Note: Separate room items / from building items
Tester_7
    BOOL_OP = OR
    COMPOSITE_TEST = 1
    TEST_CLAUSE = TEST @Value(_parent_type) = IfcSpace
    TEST_MODE = TEST
    PASSED -> CityGMLGeometrySetter_11
    FAILED -> GetGrandParentID_10
Note: Set LOD and role
CityGMLGeometrySetter_11
    GEOM = lod4Geometry
    ROLE = roomInstallation
    -> CityGMLattributeRefiner_7
Note: Set parent id
GetGrandParentID_10
    ATTR_TO_ENCODE = gml_parent_id
    DEST_ATTR = gml_parent_id
    -> CityGMLGeometrySetter_12
CityGMLGeometrySetter_12
    GEOM = lod4Geometry
    ROLE = interiorBuildingInstallation
    -> CityGMLattributeRefiner_7
CityGMLattributeRefiner_7
    DESCRIPTION = @Value(Description)
    GML_ID = @Value(gml_id)
    GML_PARENT_ID = @Value(gml_parent_id)
    -> AttributeCreator_3
AttributeCreator_3
    ATTR_TABLE:
      SET_TO fme_feature_type = IntBuildingInstallation
      SET_TO gml_parent_id = $(BuildingID)
    -> CoordinateSystemRemover

Bookmark: BuildingFurniture
IfcBuildingElementProxy (reader IFC_2)
    attributes: GlobalId char(22), Name string, Description string, ObjectType string, Tag string, CompositionType enumeration, Axis geometry, Body geometry, Box geometry, FootPrint geometry, ifc_type_object_id string
    -> ConvertGeometry_11
IfcFurnishingElement (reader IFC_2)
    attributes: GlobalId char(22), Name string, Description string, ObjectType string, Tag string, Axis geometry, Body geometry, Box geometry, FootPrint geometry, ifc_type_object_id string
    -> ConvertGeometry_11
Note: Convert Geometry to / simple surface
ConvertGeometry_11
    IFC_UNIQUE_ID = @Value(ifc_unique_id)
    -> BinaryEncoder_9
Note: Get parent type
BinaryEncoder_9
    ATTRS_TO_ENCODE = ifc_parent_unique_id
    DEST_ATTRS = _parent_id
    ENCODING_TYPE = HEX
    WRITE_TO_OTHER_ATTRS = Yes
    -> AttributeExposer_8
AttributeExposer_8
    ATTR_LIST = _parent_id
    -> VariableRetriever_8
VariableRetriever_8
    SCOPE = Global
    VALUE_ATTR = _parent_type
    VARNAME = t@Value(_parent_id)
    -> AttributeRenamer_9
Note: Set gml id
AttributeRenamer_9
    ATTR_TABLE:
      RENAME_SET_DEFAULT ifc_parent_unique_id > gml_parent_id
      RENAME_SET_DEFAULT ifc_unique_id > gml_id
    -> Tester_6
Note: Separate room items / from building items
Tester_6
    BOOL_OP = OR
    COMPOSITE_TEST = 1
    TEST_CLAUSE = TEST @Value(_parent_type) = IfcSpace
    TEST_MODE = TEST
    PASSED -> CityGMLGeometrySetter_3
    FAILED -> GetGrandParentID_9
Note: Set parent id
GetGrandParentID_9
    ATTR_TO_ENCODE = gml_parent_id
    DEST_ATTR = gml_parent_id
    -> CityGMLGeometrySetter_3
Note: Set LOD and role
CityGMLGeometrySetter_3
    GEOM = lod4Geometry
    ROLE = interiorFurniture
    -> CityGMLattributeRefiner
CityGMLattributeRefiner
    DESCRIPTION = @Value(Description)
    GML_ID = @Value(gml_id)
    GML_PARENT_ID = @Value(gml_parent_id)
    -> AttributeCreator_4
AttributeCreator_4
    ATTR_TABLE:
      SET_TO fme_feature_type = BuildingFurniture
      SET_TO gml_parent_id = $(CityModelID)
    -> CoordinateSystemRemover

Bookmark: Door
IfcDoor (reader IFC_2)
    attributes: GlobalId char(22), Name string, Description string, ObjectType string, Tag string, OverallHeight real, OverallWidth real, Axis geometry, Body geometry, Box geometry, FootPrint geometry, ifc_type_object_id string
    -> ConvertGeometry_5
Note: Convert Geometry to / simple surface
ConvertGeometry_5
    IFC_UNIQUE_ID = @Value(ifc_unique_id)
    -> BinaryEncoder_4
Note: Get parent type
BinaryEncoder_4
    ATTRS_TO_ENCODE = ifc_parent_unique_id
    DEST_ATTRS = _parent_id
    ENCODING_TYPE = HEX
    WRITE_TO_OTHER_ATTRS = Yes
    -> AttributeExposer_3
AttributeExposer_3
    ATTR_LIST = _parent_id
    -> VariableRetriever_3
VariableRetriever_3
    SCOPE = Global
    VALUE_ATTR = _parent_type
    VARNAME = t@Value(_parent_id)
    -> AttributeRenamer_13
Note: Set gml id
AttributeRenamer_13
    ATTR_TABLE:
      RENAME_SET_DEFAULT ifc_parent_unique_id > gml_parent_id
      RENAME_SET_DEFAULT ifc_unique_id > gml_id
    -> Tester_2
Note: Separate wall doors from / curtain wall doors
Tester_2
    BOOL_OP = OR
    COMPOSITE_TEST = 1
    TEST_CLAUSE = TEST @Value(_parent_type) NOT_= IfcCurtainWall
    TEST_MODE = TEST
    PASSED -> GetGrandParentID
Note: Set parent id
GetGrandParentID
    ATTR_TO_ENCODE = gml_parent_id
    DEST_ATTR = gml_parent_id
    -> CityGMLGeometrySetter_6
Note: Set LOD and role
CityGMLGeometrySetter_6
    GEOM = lod4MultiSurface
    ROLE = opening
    -> CityGMLattributeRefiner_2
CityGMLattributeRefiner_2
    DESCRIPTION = @Value(Description)
    GML_ID = @Value(gml_id)
    GML_PARENT_ID = @Value(gml_parent_id)
    -> AttributeCreator_5
AttributeCreator_5
    ATTR_TABLE = SET_TO fme_feature_type = Door
    -> CoordinateSystemRemover

Bookmark: Roof and floor
IfcRoof (reader IFC_2)
    attributes: GlobalId char(22), Name string, Description string, ObjectType string, Tag string, ShapeType enumeration, Axis geometry, Body geometry, Box geometry, FootPrint geometry, ifc_type_object_id string
    -> AttributeRenamer_7
Note: Set gml id
AttributeRenamer_7
    ATTR_TABLE = RENAME_SET_DEFAULT ifc_unique_id > gml_id
    -> FeatureMerger_2 [REQUESTOR]
IfcSlab (reader IFC_2)
    attributes: GlobalId char(22), Name string, Description string, ObjectType string, Tag string, PredefinedType enumeration, Axis geometry, Body geometry, Box geometry, FootPrint geometry, ifc_type_object_id string
    -> GeometryPartExtractor_3
Note: Get parent type
BinaryEncoder_5
    ATTRS_TO_ENCODE = ifc_parent_unique_id
    DEST_ATTRS = _parent_id
    ENCODING_TYPE = HEX
    WRITE_TO_OTHER_ATTRS = Yes
    -> AttributeExposer_4
AttributeExposer_4
    ATTR_LIST = _parent_id
    -> VariableRetriever_4
VariableRetriever_4
    SCOPE = Global
    VALUE_ATTR = _parent_type
    VARNAME = t@Value(_parent_id)
    -> AttributeFilter
Note: Routeto appropriate parent
AttributeFilter
    ATTR_NAME = _parent_type
    ATTR_VALUES = <Empty>,<Missing>,<Null>,<Unfiltered>,IfcRoof,IfcStair
    <UNFILTERED> -> AttributeRenamer_6
    IfcRoof -> FeatureMerger_2 [SUPPLIER]
    IfcStair -> FeatureMerger_3 [SUPPLIER]
Note: Add roof slab geometry onto roof
FeatureMerger_2
    JOIN_KEYS = @Value(gml_id) @Value(ifc_parent_unique_id) AUTO
    MERGE_TYPE = Geometry
    PROCESS_DUPS = NO
    REJECT_NULL_MISSING_KEYS = No
    SUPPLIERS_FIRST = No
    MERGED -> GetGrandParentID_5
Note: Set parent id
GetGrandParentID_5
    ATTR_TO_ENCODE = ifc_parent_unique_id
    DEST_ATTR = gml_parent_id
    -> CityGMLGeometrySetter
Note: Set LOD and role
CityGMLGeometrySetter
    GEOM = lod4MultiSurface
    ROLE = boundedBy
    -> CityGMLattributeRefiner_3
CityGMLattributeRefiner_3
    DESCRIPTION = @Value(Description)
    GML_ID = @Value(gml_id)
    GML_PARENT_ID = @Value(gml_parent_id)
    -> AttributeCreator_6
AttributeCreator_6
    ATTR_TABLE:
      SET_TO fme_feature_type = RoofSurface
      SET_TO gml_parent_id = $(BuildingID)
    -> CoordinateSystemRemover
Note: Set gml id
AttributeRenamer_6
    ATTR_TABLE = RENAME_SET_DEFAULT ifc_unique_id > gml_id
    -> GetGrandParentID_4
Note: Set parent id
GetGrandParentID_4
    ATTR_TO_ENCODE = ifc_parent_unique_id
    DEST_ATTR = gml_parent_id
    -> CityGMLGeometrySetter_4
Note: Set LOD and role
CityGMLGeometrySetter_4
    GEOM = lod4MultiSurface
    ROLE = boundedBy
    -> CityGMLattributeRefiner_4
CityGMLattributeRefiner_4
    DESCRIPTION = @Value(Description)
    GML_ID = @Value(gml_id)
    GML_PARENT_ID = @Value(gml_parent_id)
    -> AttributeCreator_7
AttributeCreator_7
    ATTR_TABLE:
      SET_TO fme_feature_type = FloorSurface
      SET_TO gml_parent_id = $(BuildingID)
    -> CoordinateSystemRemover

Bookmark: ConvertGeometry
GeometryPartExtractor_3
    GQUERY:
      for $geom in //geometry
      where $geom/@fme_geometry_name = 'Body'
      return number($geom/@fme_id)
    EXTRACTED -> Sampler
Sampler
    RATE = 13
    SAMPLE_MODE = No
    SAMPLE_TYPE_LONG = First N Features
    SAMPLED -> GeometryCoercer_3
    NOT_SAMPLED -> Sampler_2
Sampler_2
    RATE = 1
    SAMPLE_MODE = No
    SAMPLE_TYPE_LONG = First N Features
    SAMPLED -> SolidBuilder
    NOT_SAMPLED -> GeometryCoercer_3
SolidBuilder
    ACCUM_ATTRS_NAME = Use Attributes From One Feature
    DROP_HOLES = No
    HOLE_ATTR = _is_void
    SOLID -> GeometryCoercer_3
GeometryCoercer_3
    GQUERY:
      for $geom in //geometry
      where $geom/@fme_geometry_type = 'IFMEExtrusion'
      or $geom/@fme_geometry_type = 'IFMEBRepSolid'
      return number($geom/@fme_id)
    KIND = fme_composite_surface
    COERCED -> Deaggregator
Deaggregator
    ATTR_ACCUM_MODE = Merge List Attributes
    ATTR_CONFLICT_RES = Use List Attribute Values
    EXPLODE_INSTANCES = Yes
    GEOM_NAME_FIELD = _geometry_name
    LIST_ATTR_MODE_LOOKUP = LEAN
    MODE = Flatten All Levels
    SPLIT_COMPOSITES = No
    DEAGGREGATED -> Aggregator
Aggregator
    ACCUM_ATTRS_NAME = Merge Incoming Attributes
    AGGREGATE_TYPE = Homogeneous Collection (If Possible)
    GROUP_BY = ifc_unique_id
    MODE = Geometry - Assemble One Level
    SEP = ,
    AGGREGATE -> GeometryRefiner_3
GeometryRefiner_3
    -> BinaryEncoder_5

Bookmark: BuildingInstallation
IfcColumn (reader IFC_2)
    attributes: GlobalId char(22), Name string, Description string, ObjectType string, Tag string, Axis geometry, Body geometry, Box geometry, FootPrint geometry, ifc_type_object_id string
    -> ConvertGeometry_7
IfcBeam (reader IFC_2)
    attributes: GlobalId char(22), Name string, Description string, ObjectType string, Tag string, Axis geometry, Body geometry, Box geometry, FootPrint geometry, ifc_type_object_id string
    -> ConvertGeometry_7
Note: Convert Geometry to / simple surface
ConvertGeometry_7
    IFC_UNIQUE_ID = @Value(ifc_unique_id)
    -> BinaryEncoder_6
Note: Get parent type
BinaryEncoder_6
    ATTRS_TO_ENCODE = ifc_parent_unique_id
    DEST_ATTRS = _parent_id
    ENCODING_TYPE = HEX
    WRITE_TO_OTHER_ATTRS = Yes
    -> AttributeExposer_5
AttributeExposer_5
    ATTR_LIST = _parent_id
    -> VariableRetriever_5
VariableRetriever_5
    SCOPE = Global
    VALUE_ATTR = _parent_type
    VARNAME = t@Value(_parent_id)
    -> Tester_4
IfcRailing (reader IFC_2)
    attributes: GlobalId char(22), Name string, Description string, ObjectType string, Tag string, PredefinedType enumeration, Axis geometry, Body geometry, Box geometry, FootPrint geometry, ifc_type_object_id string
    -> ConvertGeometry_8
ConvertGeometry_8
    IFC_UNIQUE_ID = @Value(ifc_unique_id)
    -> BinaryEncoder_7
BinaryEncoder_7
    ATTRS_TO_ENCODE = ifc_parent_unique_id
    DEST_ATTRS = _parent_id
    ENCODING_TYPE = HEX
    WRITE_TO_OTHER_ATTRS = Yes
    -> AttributeExposer_6
AttributeExposer_6
    ATTR_LIST = _parent_id
    -> VariableRetriever_6
VariableRetriever_6
    SCOPE = Global
    VALUE_ATTR = _parent_type
    VARNAME = t@Value(_parent_id)
    -> Tester_5
Note: Separate stair railings / from builiding railings
Tester_5
    BOOL_OP = OR
    COMPOSITE_TEST = 1
    TEST_CLAUSE = TEST @Value(_parent_type) = IfcStair
    TEST_MODE = TEST
    PASSED -> FeatureMerger_3 [SUPPLIER]
    FAILED -> Tester_4
Note: Part of assembly?
Tester_4
    BOOL_OP = OR
    COMPOSITE_TEST = 1
    TEST_CLAUSE = TEST @Value(_parent_type) = IfcElementAssembly
    TEST_MODE = TEST
    PASSED -> GetGrandParentID_6
    FAILED -> AttributeRenamer_3
Note: Get interim parent
GetGrandParentID_6
    ATTR_TO_ENCODE = ifc_parent_unique_id
    DEST_ATTR = gml_parent_id
    -> AttributeRenamer_3
IfcStairFlight (reader IFC_2)
    attributes: GlobalId char(22), Name string, Description string, ObjectType string, Tag string, NumberOfRiser int, NumberOfTreads int, RiserHeight real, TreadLength real, Axis geometry, Body geometry, Box geometry, FootPrint geometry, ifc_type_object_id string
    -> ConvertGeometry_9
ConvertGeometry_9
    IFC_UNIQUE_ID = @Value(ifc_unique_id)
    -> FeatureMerger_3 [SUPPLIER]
IfcStair (reader IFC_2)
    attributes: GlobalId char(22), Name string, Description string, ObjectType string, Tag string, ShapeType enumeration, Axis geometry, Body geometry, Box geometry, FootPrint geometry, ifc_type_object_id string
    -> FeatureMerger_3 [REQUESTOR]
FeatureMerger_3
    GEOM_TYPE = Build Aggregates
    JOIN_KEYS = @Value(ifc_unique_id) @Value(ifc_parent_unique_id) AUTO
    MERGE_TYPE = Geometry
    PROCESS_DUPS = YES
    REJECT_NULL_MISSING_KEYS = No
    SUPPLIERS_FIRST = No
    MERGED -> BinaryEncoder_8
Note: Get parent type
BinaryEncoder_8
    ATTRS_TO_ENCODE = ifc_parent_unique_id
    DEST_ATTRS = _parent_id
    ENCODING_TYPE = HEX
    WRITE_TO_OTHER_ATTRS = Yes
    -> AttributeExposer_7
AttributeExposer_7
    ATTR_LIST = _parent_id
    -> VariableRetriever_7
VariableRetriever_7
    SCOPE = Global
    VALUE_ATTR = _parent_type
    VARNAME = t@Value(_parent_id)
    -> AttributeRenamer_3
Note: Set gml id
AttributeRenamer_3
    ATTR_TABLE = RENAME_SET_DEFAULT ifc_unique_id > gml_id
    -> AttributeExposer_10
AttributeExposer_10
    ATTR_LIST = gml_parent_id
    -> GetGrandParentID_7
Note: Set parent id
GetGrandParentID_7
    ATTR_TO_ENCODE = gml_parent_id
    DEST_ATTR = gml_parent_id
    -> CityGMLGeometrySetter_10
Note: Set LOD and role
CityGMLGeometrySetter_10
    GEOM = lod4Geometry
    ROLE = interiorBuildingInstallation
    -> CityGMLattributeRefiner_5
CityGMLattributeRefiner_5
    DESCRIPTION = @Value(Description)
    GML_ID = @Value(gml_id)
    GML_PARENT_ID = @Value(gml_parent_id)
    -> AttributeCreator_8
AttributeCreator_8
    ATTR_TABLE:
      SET_TO fme_feature_type = IntBuildingInstallation
      SET_TO gml_parent_id = $(BuildingID)
    -> CoordinateSystemRemover

Bookmark: WallSurface
IfcMember (reader IFC_2)
    attributes: GlobalId char(22), Name string, Description string, ObjectType string, Tag string, Axis geometry, Body geometry, Box geometry, FootPrint geometry, ifc_type_object_id string
    -> ConvertGeometry_3
Note: Convert Geometry to / simple surface
ConvertGeometry_3
    IFC_UNIQUE_ID = @Value(ifc_unique_id)
    -> BinaryEncoder_3
Note: Get parent type
BinaryEncoder_3
    ATTRS_TO_ENCODE = ifc_parent_unique_id
    DEST_ATTRS = _parent_id
    ENCODING_TYPE = HEX
    WRITE_TO_OTHER_ATTRS = Yes
    -> AttributeExposer_2
AttributeExposer_2
    ATTR_LIST = _parent_id
    -> VariableRetriever_2
VariableRetriever_2
    SCOPE = Global
    VALUE_ATTR = _parent_type
    VARNAME = t@Value(_parent_id)
    -> Tester
Note: Separate curtain wall memebrs / from Stair members
Tester
    BOOL_OP = OR
    COMPOSITE_TEST = 1
    TEST_CLAUSE = TEST @Value(_parent_type) = IfcCurtainWall
    TEST_MODE = TEST
    PASSED -> FeatureMerger [SUPPLIER]
    FAILED -> FeatureMerger_3 [SUPPLIER]
IfcWallStandardCase (reader IFC_2)
    attributes: GlobalId char(22), Name string, Description string, ObjectType string, Tag string, Axis geometry, Body geometry, Box geometry, FootPrint geometry, ifc_type_object_id string
    -> ConvertGeometry
IfcWall (reader IFC_2)
    attributes: GlobalId char(22), Name string, Description string, ObjectType string, Tag string, Axis geometry, Body geometry, Box geometry, FootPrint geometry, ifc_type_object_id string
    -> ConvertGeometry
ConvertGeometry
    IFC_UNIQUE_ID = @Value(ifc_unique_id)
    -> AttributeRenamer_4
IfcCurtainWall (reader IFC_2)
    attributes: GlobalId char(22), Name string, Description string, ObjectType string, Tag string, Axis geometry, Body geometry, Box geometry, FootPrint geometry, ifc_type_object_id string
    -> ConvertGeometry_6
Note: Convert Geometry to / simple surface
ConvertGeometry_6
    IFC_UNIQUE_ID = @Value(ifc_unique_id)
    -> FeatureMerger [REQUESTOR]
FeatureMerger
    GEOM_TYPE = Build Aggregates
    JOIN_KEYS = @Value(ifc_unique_id) @Value(ifc_parent_unique_id) AUTO
    MERGE_TYPE = Geometry
    PROCESS_DUPS = YES
    REJECT_NULL_MISSING_KEYS = No
    SUPPLIERS_FIRST = No
    MERGED -> AttributeRenamer_4
Note: Set gml id
AttributeRenamer_4
    ATTR_TABLE = RENAME_SET_DEFAULT ifc_unique_id > gml_id
    -> GetGrandParentID_3
Note: Set parent id
GetGrandParentID_3
    ATTR_TO_ENCODE = ifc_parent_unique_id
    DEST_ATTR = gml_parent_id
    -> CityGMLGeometrySetter_5
Note: Set LOD and role
CityGMLGeometrySetter_5
    GEOM = lod4MultiSurface
    ROLE = boundedBy
    -> CityGMLattributeRefiner_6
CityGMLattributeRefiner_6
    DESCRIPTION = @Value(Description)
    GML_ID = @Value(gml_id)
    GML_PARENT_ID = @Value(gml_parent_id)
    -> AttributeCreator_9
AttributeCreator_9
    ATTR_TABLE:
      SET_TO fme_feature_type = WallSurface
      SET_TO gml_parent_id = $(BuildingID)
    -> CoordinateSystemRemover

FME custom transformer GetGrandParentID

Parameters:
- ATTR_TO_ENCODE =   # "" Source ID
- DEST_ATTR = gml_parent_id   # TYPE:varchar(200) Destination Attribute

Input (input)
    -> BinaryEncoder_3
BinaryEncoder_3
    ATTRS_TO_ENCODE = $(ATTR_TO_ENCODE)
    DEST_ATTRS = _parent_id
    ENCODING_TYPE = HEX
    WRITE_TO_OTHER_ATTRS = Yes
    -> AttributeExposer_2
AttributeExposer_2
    ATTR_LIST = _parent_id
    -> VariableRetriever_5
VariableRetriever_5
    SCOPE = Global
    VALUE_ATTR = _gparent_id
    VARNAME = p@Value(_parent_id)
    -> BinaryDecoder
BinaryDecoder
    ATTRS_TO_DECODE = _gparent_id
    ATTR_ENCODING = utf-8
    DEST_ATTRS = $(DEST_ATTR)
    ENCODING_TYPE = HEX
    WRITE_TO_OTHER_ATTRS = Yes
    -> AttributeExposer_12
AttributeExposer_12
    ATTR_LIST = $(DEST_ATTR)
    -> Output (output)
Output (output)

FME custom transformer ConvertGeometry

Parameters:
- IFC_UNIQUE_ID = @Value(ifc_unique_id)   # Ifc Unique Id

Input (input)
    -> GeometryPartExtractor_3
Note: GeometryPartExtractor_3 [GeometryPartExtractor] / Geometry Part Selection: / Geometry XQuery: for$geomin//geometrywhere$geom/@fme_geometry_name='Body'returnnumber($geom/@fme_id)
GeometryPartExtractor_3
    GQUERY:
      for $geom in //geometry
      where $geom/@fme_geometry_name = 'Body'
      return number($geom/@fme_id)
    EXTRACTED -> SurfaceBuilder
SurfaceBuilder
    DROP_HOLES = No
    ENABLE_TOLERANCE = No
    HOLE_ATTR = _is_hole
    HOLE_LIST_ATTRS_TO_INCLUDE_MODE = Selected Attributes
    SURFACE -> GeometryCoercer_3
    <REJECTED> -> Orientor
Orientor
    FLIP_APPEARANCES_CHOICE = Yes
    KIND = REVERSE
    ORIENTED -> GeometryCoercer_3
Note: GeometryCoercer_3 [GeometryCoercer] / Geometry Type Output: / Geometry Type: fme_composite_surface / Geometry Part Selection: / Geometry XQuery: for$geomin//geometrywhere$geom/@fme_geometry_type='IFMEExtrusion'or$geom/@fme_geometry_type='IFMEBRepSolid'returnnumber($geom/@fme_id)
GeometryCoercer_3
    GQUERY:
      for $geom in //geometry
      where $geom/@fme_geometry_type = 'IFMEExtrusion'
      or $geom/@fme_geometry_type = 'IFMEBRepSolid'
      return number($geom/@fme_id)
    KIND = fme_composite_surface
    COERCED -> Deaggregator
    UNTOUCHED -> Deaggregator
Deaggregator
    ATTR_ACCUM_MODE = Merge List Attributes
    ATTR_CONFLICT_RES = Use List Attribute Values
    EXPLODE_INSTANCES = Yes
    GEOM_NAME_FIELD = _geometry_name
    LIST_ATTR_MODE_LOOKUP = LEAN
    MODE = Flatten All Levels
    SPLIT_COMPOSITES = No
    DEAGGREGATED -> Aggregator
Aggregator
    ACCUM_ATTRS_NAME = Merge Incoming Attributes
    AGGREGATE_TYPE = Homogeneous Collection (If Possible)
    GROUP_BY = ifc_unique_id
    MODE = Geometry - Assemble One Level
    SEP = ,
    AGGREGATE -> GeometryRefiner_3
GeometryRefiner_3
    -> Output (output)
Output (output)

FME custom transformer CityGMLGeometrySetter

Parameters:
- GEOM =   # CityGML Lod Name
- ROLE =   # Feature Role

INPUT (input)
    -> AttributeCreator
Note: AttributeCreator [AttributeCreator] / Attributes To Create: New AttributeAttribute Valuecitygml_lod_name$(GEOM)citygml_feature_role$(ROLE)
AttributeCreator
    ATTR_TABLE:
      SET_TO citygml_lod_name = $(GEOM)
      SET_TO citygml_feature_role = $(ROLE)
    -> GeometryPropertySetter
Note: GeometryPropertySetter [GeometryPropertySetter] / Geometry Part Selection: / Geometry XQuery: <All Parts> / General Parameters: / Property to Set: Traits From Attributes / Overwrite Existing Properties: Yes / Remove Attributes: No / Traits from Attributes Parameters: / Source Attributes: citygml_lod_name
GeometryPropertySetter
    OVERWRITE_CHOICE = Yes
    REMOVE_ATTRIBUTE = No
    SETTYPE_PARAM = Traits From Attributes
    SRC_ATTRS = citygml_lod_name
    SET -> OUTPUT (output)
OUTPUT (output)

FME custom transformer CityGMLattributeRefiner

Parameters:
- GML_PARENT_ID = @Value(gml_parent_id)   # Gml Parent Id
- DESCRIPTION = @Value(Description)   # Description
- GML_ID = @Value(gml_id)   # Gml Id

Input (input)
    -> AttributeExposer
AttributeExposer
    ATTR_LIST = _parent_id,Body,ifc_id,ifc_parent_id,Axis,FootPrint,_geometry_name,Box,_gparent_id,fme_rejection_code,_is_hole,ifc_type_object_id,Tag,ObjectType,GlobalId,_parent_type,Name,Description,OverallHeight,OverallWidth,ifc_unique_id,ifc_parent_unique_id,ShapeType,_is_void,PredefinedType,fme_feature_type
    -> AttributeCreator_5
Note: AttributeCreator_5 [AttributeCreator] / Attributes To Create: New AttributeAttribute Valuegml_idID_@Value(gml_id)gml_parent_idID_@Value(gml_parent_id)gml_description@Value(Description)gml_name@Value(Name)
AttributeCreator_5
    ATTR_TABLE:
      SET_TO gml_id = ID_@Value(gml_id)
      SET_TO gml_parent_id = ID_@Value(gml_parent_id)
      SET_TO gml_description = @Value(Description)
      SET_TO gml_name = @Value(Name)
    -> AttributeRemover_5
AttributeRemover_5
    REMOVE_ATTRS = _geometry_name,_parent_id,fme_rejection_code,Body,ifc_type_object_id,_gparent_id,PredefinedType,ObjectType,Tag,fme_feature_type,ifc_parent_id,_is_void,FootPrint,Box,Description,OverallHeight,ifc_unique_id,OverallWidth,Axis,ifc_parent_unique_id,ifc_id,_parent_type,ShapeType,_is_hole
    -> StringReplacer_2
Note: StringReplacer_2 [StringReplacer] / Parameters: / Attributes: gml_parent_id,gml_id / Mode: Replace Text / Case Sensitive: No / Text To Replace: $ / Replacement Text: S / If Attribute Value Does Not Contain Text: / Set Attribute Value To: <Do Nothing>
StringReplacer_2
    CASE = NO
    FIND_TEXT = $
    NO_MATCH = _FME_NO_OP_
    REGEXP = NO
    REPLACE_TEXT = S
    SRC_ATTRS = gml_parent_id,gml_id
    -> Output (output)
Output (output)
